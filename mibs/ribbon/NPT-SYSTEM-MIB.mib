-- File Name : NPT-SYSTEM-MIB
-- Date      : Fri Jun 03 19:12:03 CST 2011
-- Author    : AdventNet Agent Toolkit C Edition - MibEditor 6



NPT-SYSTEM-MIB	DEFINITIONS ::= BEGIN
	IMPORTS
		nptSystem
			FROM NPT-ROOT-MIB
		NPTSfpOperStatus,NPTSfpLaserTrStatus,NPTSfpLOSStatus,NPTSfpFiberType,NPTSNMPYesOrNo,NPTSNMPEnable,NPTSfpLineCode
			FROM NPT-TC-MIB
		RowStatus, DisplayString, TruthValue
			FROM SNMPv2-TC
		DisplayString
			FROM RFC1213-MIB
		MODULE-IDENTITY, enterprises, OBJECT-TYPE, Integer32, OBJECT-IDENTITY, Unsigned32
			FROM SNMPv2-SMI;

	nptSystemModule	MODULE-IDENTITY
		LAST-UPDATED	"201105240945Z"
		ORGANIZATION	"Ribbon Communications Inc."
		CONTACT-INFO	"on.support@rbbn.com 
                         Ribbon Communications Inc.,China
                         Dongxin Tower, No.398 Wensan Road, 
                         Hangzhou, 310012 P.R.China"
		DESCRIPTION		"Description"
		REVISION		"201105240945Z"
		DESCRIPTION		""
		::=  {  nptSystem  1  }

	nptMibVersion	OBJECT-TYPE	
		SYNTAX			DisplayString
		MAX-ACCESS		read-only
		STATUS			current
		DESCRIPTION		"Description"
		::=  {  nptSystemModule  1  }

	nptNESoftwareVersion	OBJECT-TYPE	
		SYNTAX			DisplayString
		MAX-ACCESS		read-only
		STATUS			current
		DESCRIPTION		"Description"
		::=  {  nptSystemModule  2  }

	nptBoardInfoTable	OBJECT-TYPE
		SYNTAX		SEQUENCE  OF  NptBoardInfoEntry
		MAX-ACCESS	not-accessible
		STATUS		current
		DESCRIPTION	"Description"
		::=  { nptSystemModule  3 }
		
	nptSysTrapConfig	OBJECT-IDENTITY
		STATUS			current
		DESCRIPTION		"This node contains the alarm configurations for the Npt equipment."
		::=  {  nptSystemModule  4  }
        
	nptCpuInfoTable	OBJECT-TYPE
		SYNTAX		SEQUENCE  OF  NptCpuInfoEntry
		MAX-ACCESS	not-accessible
		STATUS		current
		DESCRIPTION	"Description"
		::=  { nptSystemModule  5 }
		
	nptMemoryInfoTable	OBJECT-TYPE
		SYNTAX		SEQUENCE  OF  NptMemoryInfoEntry
		MAX-ACCESS	not-accessible
		STATUS		current
		DESCRIPTION	"Description"
		::=  { nptSystemModule  6 }
        
	nptSysStartTime	OBJECT-TYPE	
		SYNTAX			DisplayString
		MAX-ACCESS		read-only
		STATUS			current
		DESCRIPTION		"Description"
		::=  {  nptSystemModule  7  }

	nptTransceiverInformation OBJECT-IDENTITY
		STATUS		current
		DESCRIPTION	"Description"
		::=  {	nptSystemModule  8  }

	nptPowerConsumption	OBJECT-IDENTITY
		STATUS		current
		DESCRIPTION	"Description"
		::=  { nptSystemModule  9 }
        
	nptChassisEnvironment	OBJECT-IDENTITY
		STATUS		current
		DESCRIPTION	"Description"
		::=  { nptSystemModule  10 }
        
	nptBoardInfoEntry	OBJECT-TYPE
		SYNTAX		NptBoardInfoEntry
		MAX-ACCESS	not-accessible
		STATUS		current
		DESCRIPTION	"Row Description"
		INDEX		{  nptSlotId  }
		::=  { nptBoardInfoTable 1 }

	NptBoardInfoEntry  ::=  SEQUENCE {
		nptSlotId  Integer32,
		nptPhysicalBoardType  DisplayString,
		nptLogicalBoardType  DisplayString,
		nptCardDescription  DisplayString,
		nptCardSerialNumber  DisplayString,
		nptHwRevision  DisplayString,
		nptHwOption  DisplayString,
		nptEPLDRevision  DisplayString,
		nptBootVersion  DisplayString,
		nptFPGAVersion  DisplayString,
		nptSWRevision  DisplayString,
		nptVendor  DisplayString,
		nptMacAddress  DisplayString
		}


	nptSlotId	OBJECT-TYPE	
		SYNTAX			Integer32  ( -2147483648 .. 2147483647  ) 
		MAX-ACCESS		read-only
		STATUS			current
		DESCRIPTION		"Column Description"
		::=  {  nptBoardInfoEntry  1  }


	nptPhysicalBoardType	OBJECT-TYPE	
		SYNTAX			DisplayString
		MAX-ACCESS		read-only
		STATUS			current
		DESCRIPTION		"Column Description"
		::=  {  nptBoardInfoEntry  2  }


	nptLogicalBoardType	OBJECT-TYPE	
		SYNTAX			DisplayString
		MAX-ACCESS		read-only
		STATUS			current
		DESCRIPTION		"Column Description"
		::=  {  nptBoardInfoEntry  3  }
		
	
	nptCardDescription	OBJECT-TYPE	
		SYNTAX			DisplayString
		MAX-ACCESS		read-only
		STATUS			current
		DESCRIPTION		"Column Description"
		::=  {  nptBoardInfoEntry  4  }
		
		
	nptCardSerialNumber	OBJECT-TYPE	
		SYNTAX			DisplayString
		MAX-ACCESS		read-only
		STATUS			current
		DESCRIPTION		"Column Description"
		::=  {  nptBoardInfoEntry  5  }
		
		
	
	nptHwRevision	OBJECT-TYPE	
		SYNTAX			DisplayString
		MAX-ACCESS		read-only
		STATUS			current
		DESCRIPTION		"Column Description"
		::=  {  nptBoardInfoEntry  6  }
		
	nptHwOption	OBJECT-TYPE	
		SYNTAX			DisplayString
		MAX-ACCESS		read-only
		STATUS			current
		DESCRIPTION		"Column Description"
		::=  {  nptBoardInfoEntry  7  }
		
	nptEPLDRevision	OBJECT-TYPE	
		SYNTAX			DisplayString
		MAX-ACCESS		read-only
		STATUS			current
		DESCRIPTION		"Column Description"
		::=  {  nptBoardInfoEntry  8  }
		
	nptBootVersion	OBJECT-TYPE	
		SYNTAX			DisplayString
		MAX-ACCESS		read-only
		STATUS			current
		DESCRIPTION		"Column Description"
		::=  {  nptBoardInfoEntry  9  }
		
	nptFPGAVersion	OBJECT-TYPE	
		SYNTAX			DisplayString
		MAX-ACCESS		read-only
		STATUS			current
		DESCRIPTION		"Column Description"
		::=  {  nptBoardInfoEntry  10  }
		
	nptSWRevision	OBJECT-TYPE	
		SYNTAX			DisplayString
		MAX-ACCESS		read-only
		STATUS			current
		DESCRIPTION		"Column Description"
		::=  {  nptBoardInfoEntry  11  }
		
	nptVendor	OBJECT-TYPE	
		SYNTAX			DisplayString
		MAX-ACCESS		read-only
		STATUS			current
		DESCRIPTION		"Column Description"
		::=  {  nptBoardInfoEntry  12  }
		
		
	nptMacAddress	OBJECT-TYPE	
		SYNTAX			DisplayString
		MAX-ACCESS		read-only
		STATUS			current
		DESCRIPTION		"Column Description"
		::=  {  nptBoardInfoEntry  13  }
		
	
		
	nptCpuInfoEntry	OBJECT-TYPE
		SYNTAX		NptCpuInfoEntry
		MAX-ACCESS	not-accessible
		STATUS		current
		DESCRIPTION	"Row Description"
		INDEX		{  nptCpuSlotId  }
		::=  { nptCpuInfoTable 1 }

	NptCpuInfoEntry  ::=  SEQUENCE {
		nptCpuSlotId  Integer32,
		nptCpuSlotType  DisplayString,
		nptCpuPhysicalBoardType  DisplayString,
		nptCpuType  DisplayString,
		nptCpuRevision  DisplayString,
		nptCpuSpeed  DisplayString,
		nptCpuCacheSize  DisplayString,
		nptTotalProcesses  DisplayString,
		nptProcessesStatus  DisplayString,
        nptUptime       DisplayString,
		nptLoadAverage  DisplayString,
		nptUserUtilization  DisplayString,
		nptNiceUtilization  DisplayString,
		nptSystemUtilization  DisplayString,
        nptWaitingUtilization  DisplayString,
        nptHwInterupUtilization  DisplayString,
        nptSoftInterupUtilization  DisplayString,
        nptIdle  DisplayString
		}


	nptCpuSlotId	OBJECT-TYPE	
		SYNTAX			Integer32  ( -2147483648 .. 2147483647  ) 
		MAX-ACCESS		read-only
		STATUS			current
		DESCRIPTION		"Column Description"
		::=  {  nptCpuInfoEntry  1  }

	nptCpuSlotType	OBJECT-TYPE	
		SYNTAX			DisplayString
		MAX-ACCESS		read-only
		STATUS			current
		DESCRIPTION		"Column Description"
		::=  {  nptCpuInfoEntry  2  }

	nptCpuPhysicalBoardType	OBJECT-TYPE	
		SYNTAX			DisplayString
		MAX-ACCESS		read-only
		STATUS			current
		DESCRIPTION		"Column Description"
		::=  {  nptCpuInfoEntry  3  }

	nptCpuType	OBJECT-TYPE	
		SYNTAX			DisplayString
		MAX-ACCESS		read-only
		STATUS			current
		DESCRIPTION		"Column Description"
		::=  {  nptCpuInfoEntry  4  }

	nptCpuRevision	OBJECT-TYPE	
		SYNTAX			DisplayString
		MAX-ACCESS		read-only
		STATUS			current
		DESCRIPTION		"Column Description"
		::=  {  nptCpuInfoEntry  5  }

	nptCpuSpeed	OBJECT-TYPE	
		SYNTAX			DisplayString
		MAX-ACCESS		read-only
		STATUS			current
		DESCRIPTION		"Column Description"
		::=  {  nptCpuInfoEntry  6  }

	nptCpuCacheSize	OBJECT-TYPE	
		SYNTAX			DisplayString
		MAX-ACCESS		read-only
		STATUS			current
		DESCRIPTION		"Column Description"
		::=  {  nptCpuInfoEntry  7  }

	nptTotalProcesses	OBJECT-TYPE	
		SYNTAX			DisplayString
		MAX-ACCESS		read-only
		STATUS			current
		DESCRIPTION		"Column Description"
		::=  {  nptCpuInfoEntry  8  }

	nptProcessesStatus	OBJECT-TYPE	
		SYNTAX			DisplayString
		MAX-ACCESS		read-only
		STATUS			current
		DESCRIPTION		"Column Description"
		::=  {  nptCpuInfoEntry  9  }

	nptUptime	OBJECT-TYPE	
		SYNTAX			DisplayString
		MAX-ACCESS		read-only
		STATUS			current
		DESCRIPTION		"Column Description"
		::=  {  nptCpuInfoEntry  10  }

	nptLoadAverage	OBJECT-TYPE	
		SYNTAX			DisplayString
		MAX-ACCESS		read-only
		STATUS			current
		DESCRIPTION		"Column Description"
		::=  {  nptCpuInfoEntry  11  }

	nptUserUtilization	OBJECT-TYPE	
		SYNTAX			DisplayString
		MAX-ACCESS		read-only
		STATUS			current
		DESCRIPTION		"Column Description"
		::=  {  nptCpuInfoEntry  12  }

	nptNiceUtilization	OBJECT-TYPE	
		SYNTAX			DisplayString
		MAX-ACCESS		read-only
		STATUS			current
		DESCRIPTION		"Column Description"
		::=  {  nptCpuInfoEntry  13  }

	nptSystemUtilization	OBJECT-TYPE	
		SYNTAX			DisplayString
		MAX-ACCESS		read-only
		STATUS			current
		DESCRIPTION		"Column Description"
		::=  {  nptCpuInfoEntry  14  }

	nptWaitingUtilization	OBJECT-TYPE	
		SYNTAX			DisplayString
		MAX-ACCESS		read-only
		STATUS			current
		DESCRIPTION		"Column Description"
		::=  {  nptCpuInfoEntry  15  }

	nptHwInterupUtilization	OBJECT-TYPE	
		SYNTAX			DisplayString
		MAX-ACCESS		read-only
		STATUS			current
		DESCRIPTION		"Column Description"
		::=  {  nptCpuInfoEntry  16  }

	nptSoftInterupUtilization	OBJECT-TYPE	
		SYNTAX			DisplayString
		MAX-ACCESS		read-only
		STATUS			current
		DESCRIPTION		"Column Description"
		::=  {  nptCpuInfoEntry  17  }

	nptIdle	OBJECT-TYPE	
		SYNTAX			DisplayString
		MAX-ACCESS		read-only
		STATUS			current
		DESCRIPTION		"Column Description"
		::=  {  nptCpuInfoEntry  18  }



	nptMemoryInfoEntry	OBJECT-TYPE
		SYNTAX		NptMemoryInfoEntry
		MAX-ACCESS	not-accessible
		STATUS		current
		DESCRIPTION	"Row Description"
		INDEX		{  nptMemorySlotId  }
		::=  { nptMemoryInfoTable 1 }


	NptMemoryInfoEntry  ::=  SEQUENCE {
		nptMemorySlotId  Integer32,
		nptMemorySlotType  DisplayString,
		nptMemoryPhysicalBoardType  DisplayString,
		nptMemoryFree  Integer32,
		nptMemoryUsed  Integer32,
		nptMemoryBuffers  Integer32,
		nptMemoryTotal  Integer32,
		nptMemoryFreeSwap  Integer32,
		nptMemoryUsedSwap  Integer32,
		nptMemoryCachedSwap  Integer32,
		nptMemoryTotalSwap  Integer32
		}


	nptMemorySlotId	OBJECT-TYPE	
		SYNTAX			Integer32  ( -2147483648 .. 2147483647  ) 
		MAX-ACCESS		read-only
		STATUS			current
		DESCRIPTION		"Column Description"
		::=  {  nptMemoryInfoEntry  1  }

	nptMemorySlotType	OBJECT-TYPE	
		SYNTAX			DisplayString
		MAX-ACCESS		read-only
		STATUS			current
		DESCRIPTION		"Column Description"
		::=  {  nptMemoryInfoEntry  2  }

	nptMemoryPhysicalBoardType	OBJECT-TYPE	
		SYNTAX			DisplayString
		MAX-ACCESS		read-only
		STATUS			current
		DESCRIPTION		"Column Description"
		::=  {  nptMemoryInfoEntry  3  }

	nptMemoryFree	OBJECT-TYPE	
		SYNTAX			Integer32
		MAX-ACCESS		read-only
		STATUS			current
		DESCRIPTION		"KB"
		::=  {  nptMemoryInfoEntry  4  }

	nptMemoryUsed	OBJECT-TYPE	
		SYNTAX			Integer32
		MAX-ACCESS		read-only
		STATUS			current
		DESCRIPTION		"KB"
		::=  {  nptMemoryInfoEntry  5  }

	nptMemoryBuffers	OBJECT-TYPE	
		SYNTAX			Integer32
		MAX-ACCESS		read-only
		STATUS			current
		DESCRIPTION		"KB"
		::=  {  nptMemoryInfoEntry  6  }

	nptMemoryTotal	OBJECT-TYPE	
		SYNTAX			Integer32
		MAX-ACCESS		read-only
		STATUS			current
		DESCRIPTION		"KB"
		::=  {  nptMemoryInfoEntry  7  }

	nptMemoryFreeSwap	OBJECT-TYPE	
		SYNTAX			Integer32
		MAX-ACCESS		read-only
		STATUS			current
		DESCRIPTION		"KB"
		::=  {  nptMemoryInfoEntry  8  }

	nptMemoryUsedSwap	OBJECT-TYPE	
		SYNTAX			Integer32
		MAX-ACCESS		read-only
		STATUS			current
		DESCRIPTION		"KB"
		::=  {  nptMemoryInfoEntry  9  }

	nptMemoryCachedSwap	OBJECT-TYPE	
		SYNTAX			Integer32
		MAX-ACCESS		read-only
		STATUS			current
		DESCRIPTION		"KB"
		::=  {  nptMemoryInfoEntry  10  }

	nptMemoryTotalSwap	OBJECT-TYPE	
		SYNTAX			Integer32
		MAX-ACCESS		read-only
		STATUS			current
		DESCRIPTION		"KB"
		::=  {  nptMemoryInfoEntry  11  }
		
	nptManagerTable	OBJECT-TYPE
		SYNTAX		SEQUENCE  OF  NptManagerEntry
		MAX-ACCESS	not-accessible
		STATUS		current
		DESCRIPTION	"It is possible to configure up to ten managers, 
				to whom, traps will be sent. It is possible also 
				to define trap filters for each of the managers."
		::=  { nptSysTrapConfig  4 }

	nptManagerEntry	OBJECT-TYPE
		SYNTAX		NptManagerEntry
		MAX-ACCESS	not-accessible
		STATUS		current
		DESCRIPTION	"Row definition for NptManagerTable"
		INDEX		{  nptTrapIpAddress, nptTrapPortNumber, nptTrapVersion }
		::=  { nptManagerTable 1 }

	NptManagerEntry  ::=  SEQUENCE {
		nptTrapIpAddress	DisplayString,
		nptTrapPortNumber  Unsigned32,
		nptTrapVersion  Unsigned32,
		nptIsAdministrator  Unsigned32
		}


	nptTrapIpAddress	OBJECT-TYPE	
		SYNTAX			DisplayString
		MAX-ACCESS		read-only
		STATUS			current
		DESCRIPTION		"The manager IP address. Value of 0 will disable that
					entry."
		::=  {  nptManagerEntry  1  }


	nptTrapPortNumber	OBJECT-TYPE	
		SYNTAX			Unsigned32  ( 0 .. 4294967295  ) 
		MAX-ACCESS		read-only
		STATUS			current
		DESCRIPTION		"The port number on which the manager is listening for
					traps, the default is 162."
		::=  {  nptManagerEntry  2  }


	nptTrapVersion	OBJECT-TYPE	
		SYNTAX			Unsigned32  ( 0 .. 4294967295  ) 
		MAX-ACCESS		read-only
		STATUS			current
		DESCRIPTION		"The port number on which the manager is listening for
					traps, the default is 162."
		::=  {  nptManagerEntry  3  }


	nptIsAdministrator	OBJECT-TYPE	
		SYNTAX			Unsigned32  ( 0 .. 4294967295  ) 
		MAX-ACCESS		read-only
		STATUS			current
		DESCRIPTION		"Defining a manager if it is an administrator or not.
					An administrator has rights to read,write and create.
					A common manager can read only.
					0-common manager
					1-administrator manager"
		::=  {  nptManagerEntry  4  }
		
	nptTransceiverConfigurationTable	OBJECT-TYPE	
		SYNTAX		SEQUENCE  OF  NptTransceiverConfigurationEntry
		MAX-ACCESS	not-accessible
		STATUS		current
		DESCRIPTION	"Description"
		::=  { nptTransceiverInformation  1 }
	
	nptTransceiverConfigurationEntry	OBJECT-TYPE
		SYNTAX			NptTransceiverConfigurationEntry
		MAX-ACCESS 		not-accessible
		STATUS			current
		DESCRIPTION		"Row Description"
        INDEX			{	nptTransceiverConfigurationIndex	}
		::=  { nptTransceiverConfigurationTable 1 }
	
		NptTransceiverConfigurationEntry   ::=  SEQUENCE {
		nptTransceiverConfigurationIndex	Unsigned32,
		nptTransceiverConfigurationName	DisplayString,
		nptExpectedTransceiverType	DisplayString,
		nptExpectedApplicationCode	DisplayString,
		nptRate	 DisplayString,
		nptConnectorType	DisplayString,
		nptNominalBitrate 	DisplayString,
		nptSupportedLinkLength DisplayString,
        nptTransmitedWavelength DisplayString,
		nptChannelColor	DisplayString,
		nptSupportedFiberType	DisplayString
		}
        
	nptTransceiverConfigurationIndex	OBJECT-TYPE	
		SYNTAX		Unsigned32  ( 0 .. 4294967295  )
		MAX-ACCESS	read-only
		STATUS		current
		DESCRIPTION	"TransceiverConfiguration Index"
		::=  {  nptTransceiverConfigurationEntry  1  }
		
	nptTransceiverConfigurationName	OBJECT-TYPE	
		SYNTAX		DisplayString
		MAX-ACCESS	read-only
		STATUS		current
		DESCRIPTION	"TransceiverConfiguration Name"
		::=  {  nptTransceiverConfigurationEntry  2  }
		
	nptExpectedTransceiverType	OBJECT-TYPE	
		SYNTAX		DisplayString
		MAX-ACCESS	read-only
		STATUS		current
		DESCRIPTION	"Expected Transceiver Type"
		::=  {  nptTransceiverConfigurationEntry  3  }
		
	nptExpectedApplicationCode	OBJECT-TYPE	
		SYNTAX		DisplayString
		MAX-ACCESS	read-only
		STATUS		current
		DESCRIPTION	"Expected Transceiver Code"
		::=  {  nptTransceiverConfigurationEntry  4  }
		
	nptRate	OBJECT-TYPE	
		SYNTAX		DisplayString
		MAX-ACCESS	read-only
		STATUS		current
		DESCRIPTION	"Rate"
		::=  {  nptTransceiverConfigurationEntry  5  }
		
	nptConnectorType	OBJECT-TYPE	
		SYNTAX		DisplayString
		MAX-ACCESS	read-only
		STATUS		current
		DESCRIPTION	"Connector Type"
		::=  {  nptTransceiverConfigurationEntry  6  }
		
	nptNominalBitrate 	OBJECT-TYPE	
		SYNTAX		DisplayString
		MAX-ACCESS	read-only
		STATUS		current
		DESCRIPTION	"Nominal Bitrate"
		::=  {  nptTransceiverConfigurationEntry  7  }
		
	nptSupportedLinkLength	OBJECT-TYPE	
		SYNTAX		DisplayString
		MAX-ACCESS	read-only
		STATUS		current
		DESCRIPTION	"Supported Link Length"
		::=  {  nptTransceiverConfigurationEntry  8  }
		
	nptTransmitedWavelength	OBJECT-TYPE	
		SYNTAX		DisplayString
		MAX-ACCESS	read-only
		STATUS		current
		DESCRIPTION	"Transmited Wavelength"
		::=  {  nptTransceiverConfigurationEntry  9  }
		
	nptChannelColor	OBJECT-TYPE	
		SYNTAX		DisplayString
		MAX-ACCESS	read-only
		STATUS		current
		DESCRIPTION	"Channel Color"
		::=  {  nptTransceiverConfigurationEntry  10  }
	
	nptSupportedFiberType	OBJECT-TYPE	
		SYNTAX		DisplayString
		MAX-ACCESS	read-only
		STATUS		current
		DESCRIPTION	"Supported Fiber Type"
		::=  {  nptTransceiverConfigurationEntry  11  }
		
	nptTransceiverStatusTable	OBJECT-TYPE	
		SYNTAX		SEQUENCE  OF  NptTransceiverStatusEntry
		MAX-ACCESS	not-accessible
		STATUS		current
		DESCRIPTION	"Description"
		::=  { nptTransceiverInformation  2 }
	
	nptTransceiverStatusEntry	OBJECT-TYPE
		SYNTAX			NptTransceiverStatusEntry
		MAX-ACCESS 		not-accessible
		STATUS			current
		DESCRIPTION		"Row Description"
        INDEX			{	nptTransceiverStatusIndex	}
		::=  { nptTransceiverStatusTable 1 }
		
	NptTransceiverStatusEntry   ::=  SEQUENCE {
		nptTransceiverStatusIndex	Unsigned32,
		nptTransceiverStatusName	DisplayString,
		nptOperationalState 	NPTSfpOperStatus,
		nptActualLaserTransmitStatus 	NPTSfpLaserTrStatus,
		nptReceivedLOSStatus 	 NPTSfpLOSStatus,
		nptActualNominalBitrate 	Integer32,
		nptActualSupportedLinkLength 	Integer32,
		nptActualTransmitedWavelength Integer32,
        nptActualSupportedFiberType  NPTSfpFiberType,
		nptLineCode				 	 NPTSfpLineCode,
		nptCoherent					 TruthValue,
		nptSubBand					 Integer32,
		nptMeasuredRxOSNR			 DisplayString,
		nptTxOSNR					 DisplayString
		}
        
	nptTransceiverStatusIndex	OBJECT-TYPE	
		SYNTAX		Unsigned32  ( 0 .. 4294967295  )
		MAX-ACCESS	read-only
		STATUS		current
		DESCRIPTION	"TransceiverStatus Index"
		::=  {  nptTransceiverStatusEntry  1  }
		
	nptTransceiverStatusName	OBJECT-TYPE	
		SYNTAX		DisplayString
		MAX-ACCESS	read-only
		STATUS		current
		DESCRIPTION	"TransceiverStatus Name"
		::=  {  nptTransceiverStatusEntry  2  }
		
	nptOperationalState	OBJECT-TYPE	
		SYNTAX		NPTSfpOperStatus
		MAX-ACCESS	read-only
		STATUS		current
		DESCRIPTION	"Operational State"
		::=  {  nptTransceiverStatusEntry  3  }
		
	nptActualLaserTransmitStatus	OBJECT-TYPE	
		SYNTAX		NPTSfpLaserTrStatus
		MAX-ACCESS	read-only
		STATUS		current
		DESCRIPTION	"Actual Laser Transmit Status"
		::=  {  nptTransceiverStatusEntry  4  }
		
	nptReceivedLOSStatus	OBJECT-TYPE	
		SYNTAX		NPTSfpLOSStatus
		MAX-ACCESS	read-only
		STATUS		current
		DESCRIPTION	"Received LOS Status"
		::=  {  nptTransceiverStatusEntry  5  }
		
	nptActualNominalBitrate	OBJECT-TYPE	
		SYNTAX		Integer32
		MAX-ACCESS	read-only
		STATUS		current
		DESCRIPTION	"Actual Nominal Bitrate (Mbps)"
		::=  {  nptTransceiverStatusEntry  6  }
		
	nptActualSupportedLinkLength 	OBJECT-TYPE	
		SYNTAX		Integer32
		MAX-ACCESS	read-only
		STATUS		current
		DESCRIPTION	"Actual Supported Link Length (m)"
		::=  {  nptTransceiverStatusEntry  7  }
		
	nptActualTransmitedWavelength	OBJECT-TYPE	
		SYNTAX		Integer32
		MAX-ACCESS	read-only
		STATUS		current
		DESCRIPTION	"Actual Transmited Wavelength (nm)"
		::=  {  nptTransceiverStatusEntry  8  }
		
	nptActualSupportedFiberType	OBJECT-TYPE	
		SYNTAX		NPTSfpFiberType
		MAX-ACCESS	read-only
		STATUS		current
		DESCRIPTION	"Actual Supported Fiber Type"
		::=  {  nptTransceiverStatusEntry  9  }
		
	nptLineCode	OBJECT-TYPE	
		SYNTAX		NPTSfpLineCode
		MAX-ACCESS	read-only
		STATUS		current
		DESCRIPTION	"Line Code"
		::=  {  nptTransceiverStatusEntry  10  }

	nptCoherent		OBJECT-TYPE	
		SYNTAX		Integer32
		MAX-ACCESS	read-only
		STATUS		current
		DESCRIPTION	"Coherent"
		::=  {  nptTransceiverStatusEntry  11  }
		
	nptSubBand	OBJECT-TYPE	
		SYNTAX		Integer32
		MAX-ACCESS	read-only
		STATUS		current
		DESCRIPTION	"Sub Band"
		::=  {  nptTransceiverStatusEntry  12  }	
		
	nptMeasuredRxOSNR	OBJECT-TYPE	
		SYNTAX		DisplayString
		MAX-ACCESS	read-only
		STATUS		current
		DESCRIPTION	"Measured Rx OSNR"
		::=  {  nptTransceiverStatusEntry  13  }

	nptTxOSNR	OBJECT-TYPE	
		SYNTAX		DisplayString
		MAX-ACCESS	read-only
		STATUS		current
		DESCRIPTION	"Tx OSNR"
		::=  {  nptTransceiverStatusEntry  14  }
		
	nptTransceiverInventoryTable	OBJECT-TYPE	
		SYNTAX		SEQUENCE  OF  NptTransceiverInventoryEntry
		MAX-ACCESS	not-accessible
		STATUS		current
		DESCRIPTION	"Description"
		::=  { nptTransceiverInformation  3 }
	
	nptTransceiverInventoryEntry	OBJECT-TYPE
		SYNTAX			NptTransceiverInventoryEntry
		MAX-ACCESS 		not-accessible
		STATUS			current
		DESCRIPTION		"Row Description"
        INDEX			{	nptTransceiverInventoryIndex	}
		::=  { nptTransceiverInventoryTable 1 }
		
	NptTransceiverInventoryEntry   ::=  SEQUENCE {
		nptTransceiverInventoryIndex	Unsigned32,
		nptTransceiverInventoryName	DisplayString,
		nptActualTransceiverType 	DisplayString,
		nptTransceiverInventoryVendor 	DisplayString,
		nptSerialNumber  	 DisplayString,
		nptHWRevision 	DisplayString,
		nptHWOption 	DisplayString,
		nptGeneralDescription  DisplayString,
        nptModuleSubType   DisplayString,
		nptActualApplicationCode DisplayString,
		nptSupportChannelNumber DisplayString,
		nptWDMFirstChannelnumber DisplayString,
		nptChannelSpacing DisplayString
		}
        
	nptTransceiverInventoryIndex	OBJECT-TYPE	
		SYNTAX		Unsigned32  ( 0 .. 4294967295  ) 
		MAX-ACCESS	read-only
		STATUS		current
		DESCRIPTION	"TransceiverInventory Index"
		::=  {  nptTransceiverInventoryEntry  1  }
		
	nptTransceiverInventoryName		OBJECT-TYPE	
		SYNTAX		DisplayString
		MAX-ACCESS	read-only
		STATUS		current
		DESCRIPTION	"TransceiverInventory Name"
		::=  {  nptTransceiverInventoryEntry  2  }
		
	nptActualTransceiverType	OBJECT-TYPE	
		SYNTAX		DisplayString
		MAX-ACCESS	read-only
		STATUS		current
		DESCRIPTION	"Actual Transceiver Type"
		::=  {  nptTransceiverInventoryEntry  3  }
		
	nptTransceiverInventoryVendor	OBJECT-TYPE	
		SYNTAX		DisplayString
		MAX-ACCESS	read-only
		STATUS		current
		DESCRIPTION	"Vendor"
		::=  {  nptTransceiverInventoryEntry  4  }
		
	nptSerialNumber	OBJECT-TYPE	
		SYNTAX		DisplayString
		MAX-ACCESS	read-only
		STATUS		current
		DESCRIPTION	"Serial Number"
		::=  {  nptTransceiverInventoryEntry  5  }
		
	nptHWRevision	OBJECT-TYPE	
		SYNTAX		DisplayString
		MAX-ACCESS	read-only
		STATUS		current
		DESCRIPTION	"H/W Revision"
		::=  {  nptTransceiverInventoryEntry  6  }
		
	nptHWOption 	OBJECT-TYPE	
		SYNTAX		DisplayString
		MAX-ACCESS	read-only
		STATUS		current
		DESCRIPTION	"H/W Option"
		::=  {  nptTransceiverInventoryEntry  7  }
		
	nptGeneralDescription	OBJECT-TYPE	
		SYNTAX		DisplayString
		MAX-ACCESS	read-only
		STATUS		current
		DESCRIPTION	"General Description"
		::=  {  nptTransceiverInventoryEntry  8  }
		
	nptModuleSubType	OBJECT-TYPE	
		SYNTAX		DisplayString
		MAX-ACCESS	read-only
		STATUS		current
		DESCRIPTION	"Module Sub Type"
		::=  {  nptTransceiverInventoryEntry  9  }
	
	nptActualApplicationCode	OBJECT-TYPE	
		SYNTAX		DisplayString
		MAX-ACCESS	read-only
		STATUS		current
		DESCRIPTION	"Actual Application Code"
		::=  {  nptTransceiverInventoryEntry  10  }

	nptSupportChannelNumber	OBJECT-TYPE	
		SYNTAX		DisplayString
		MAX-ACCESS	read-only
		STATUS		current
		DESCRIPTION	"Support Channel Number"
		::=  {  nptTransceiverInventoryEntry  11  }

	nptWDMFirstChannelnumber	OBJECT-TYPE	
		SYNTAX		DisplayString
		MAX-ACCESS	read-only
		STATUS		current
		DESCRIPTION	"WDM First Channel number"
		::=  {  nptTransceiverInventoryEntry  12  }

	nptChannelSpacing	OBJECT-TYPE	
		SYNTAX		DisplayString
		MAX-ACCESS	read-only
		STATUS		current
		DESCRIPTION	"Channel Spacing"
		::=  {  nptTransceiverInventoryEntry  13  }	
	
	nptTransceiverPowerTable	OBJECT-TYPE	
		SYNTAX		SEQUENCE  OF  NptTransceiverPowerEntry
		MAX-ACCESS	not-accessible
		STATUS		current
		DESCRIPTION	"Description"
		::=  { nptTransceiverInformation  4 }
	
	nptTransceiverPowerEntry	OBJECT-TYPE
		SYNTAX			NptTransceiverPowerEntry
		MAX-ACCESS 		not-accessible
		STATUS			current
		DESCRIPTION		"Row Description"
        INDEX			{	nptTransceiverPowerIndex	}
		::=  { nptTransceiverPowerTable 1 }
	
	NptTransceiverPowerEntry   ::=  SEQUENCE {
		nptTransceiverPowerIndex	Unsigned32,
		nptTransceiverPowerName	DisplayString,
		nptLaservoltage 	DisplayString,
		nptLaserbiascurrent  	DisplayString,
		nptLasertemperature   	 DisplayString,
		nptTxlaserpower  	DisplayString,
		nptRxlaserpower  	DisplayString,
		nptMaxrxpowerlane	DisplayString,
		nptMinrxpowerlane	DisplayString,
		nptMaxtxpowerlane	DisplayString,
		nptMintxpowerlane	DisplayString
		}
        
	nptTransceiverPowerIndex	OBJECT-TYPE	
		SYNTAX		Unsigned32  ( 0 .. 4294967295  ) 
		MAX-ACCESS	read-only
		STATUS		current
		DESCRIPTION	"TransceiverPower Index"
		::=  {  nptTransceiverPowerEntry  1  }
		
	nptTransceiverPowerName		OBJECT-TYPE	
		SYNTAX		DisplayString
		MAX-ACCESS	read-only
		STATUS		current
		DESCRIPTION	"TransceiverPower Name"
		::=  {  nptTransceiverPowerEntry  2  }
		
	nptLaservoltage	OBJECT-TYPE	
		SYNTAX		DisplayString
		MAX-ACCESS	read-only
		STATUS		current
		DESCRIPTION	"Laser voltage"
		::=  {  nptTransceiverPowerEntry  3  }
		
	nptLaserbiascurrent	OBJECT-TYPE	
		SYNTAX		DisplayString
		MAX-ACCESS	read-only
		STATUS		current
		DESCRIPTION	"Laser bias current"
		::=  {  nptTransceiverPowerEntry  4  }
		
	nptLasertemperature 	OBJECT-TYPE	
		SYNTAX		DisplayString
		MAX-ACCESS	read-only
		STATUS		current
		DESCRIPTION	"Laser temperature"
		::=  {  nptTransceiverPowerEntry  5  }
		
	nptTxlaserpower	OBJECT-TYPE	
		SYNTAX		DisplayString
		MAX-ACCESS	read-only
		STATUS		current
		DESCRIPTION	"Tx laser power"
		::=  {  nptTransceiverPowerEntry  6  }
		
	nptRxlaserpower 	OBJECT-TYPE	
		SYNTAX		DisplayString
		MAX-ACCESS	read-only
		STATUS		current
		DESCRIPTION	"Rx laser power"
		::=  {  nptTransceiverPowerEntry  7  }	
		
	nptMaxrxpowerlane 	OBJECT-TYPE	
		SYNTAX		DisplayString
		MAX-ACCESS	read-only
		STATUS		current
		DESCRIPTION	"Max rx power lane"
		::=  {  nptTransceiverPowerEntry  8  }	

	nptMinrxpowerlane 	OBJECT-TYPE	
		SYNTAX		DisplayString
		MAX-ACCESS	read-only
		STATUS		current
		DESCRIPTION	"Min rx power lane"
		::=  {  nptTransceiverPowerEntry  9  }	
		
	nptMaxtxpowerlane 	OBJECT-TYPE	
		SYNTAX		DisplayString
		MAX-ACCESS	read-only
		STATUS		current
		DESCRIPTION	"Max tx power lane"
		::=  {  nptTransceiverPowerEntry  10  }	

	nptMintxpowerlane 	OBJECT-TYPE	
		SYNTAX		DisplayString
		MAX-ACCESS	read-only
		STATUS		current
		DESCRIPTION	"Min tx power lane"
		::=  {  nptTransceiverPowerEntry  11  }		
	
	nptTunnableTransceiverConfigurationTable	OBJECT-TYPE	
		SYNTAX		SEQUENCE  OF  NptTunnableTransceiverConfigurationEntry
		MAX-ACCESS	not-accessible
		STATUS		current
		DESCRIPTION	"Description"
		::=  { nptTransceiverInformation  5 }
	
	nptTunnableTransceiverConfigurationEntry	OBJECT-TYPE
		SYNTAX			NptTunnableTransceiverConfigurationEntry
		MAX-ACCESS 		not-accessible
		STATUS			current
		DESCRIPTION		"Row Description"
        INDEX			{	nptTunnableTransceiverConfigurationIndex	}
		::=  { nptTunnableTransceiverConfigurationTable 1 }
		
	NptTunnableTransceiverConfigurationEntry   ::=  SEQUENCE {
		nptTunnableTransceiverConfigurationIndex	Unsigned32,
		nptTunnableTransceiverConfigurationName	DisplayString,
		nptChannelFrequency 	Integer32,
		nptWavelength  	DisplayString,
		nptTxDither   	 NPTSNMPEnable,
		nptFrequencyTuning  	NPTSNMPYesOrNo,
		nptWavelengthTuning  	NPTSNMPYesOrNo,
		nptTxDitherSupport		NPTSNMPYesOrNo,
		nptFirstFrequency		DisplayString,
		nptLastFrequency		DisplayString,
		nptMinimumSupportedGridSpacing	DisplayString
		}
        
	nptTunnableTransceiverConfigurationIndex	OBJECT-TYPE	
		SYNTAX		Unsigned32  ( 0 .. 4294967295  ) 
		MAX-ACCESS	read-only
		STATUS		current
		DESCRIPTION	"TunnableTransceiverConfiguration Index"
		::=  {  nptTunnableTransceiverConfigurationEntry  1  }
		
	nptTunnableTransceiverConfigurationName		OBJECT-TYPE	
		SYNTAX		DisplayString
		MAX-ACCESS	read-only
		STATUS		current
		DESCRIPTION	"TunnableTransceiverConfiguration Name"
		::=  {  nptTunnableTransceiverConfigurationEntry  2  }
		
	nptChannelFrequency	OBJECT-TYPE	
		SYNTAX		Integer32
		MAX-ACCESS	read-only
		STATUS		current
		DESCRIPTION	"Channel Frequency (GHz)"
		::=  {  nptTunnableTransceiverConfigurationEntry  3  }
		
	nptWavelength	OBJECT-TYPE	
		SYNTAX		DisplayString
		MAX-ACCESS	read-only
		STATUS		current
		DESCRIPTION	"Wavelength"
		::=  {  nptTunnableTransceiverConfigurationEntry  4  }
		
	nptTxDither 	OBJECT-TYPE	
		SYNTAX		NPTSNMPEnable
		MAX-ACCESS	read-only
		STATUS		current
		DESCRIPTION	"TxDither"
		::=  {  nptTunnableTransceiverConfigurationEntry  5  }
		
	nptFrequencyTuning	OBJECT-TYPE	
		SYNTAX		NPTSNMPYesOrNo
		MAX-ACCESS	read-only
		STATUS		current
		DESCRIPTION	"Frequency Tuning"
		::=  {  nptTunnableTransceiverConfigurationEntry  6  }
		
	nptWavelengthTuning 	OBJECT-TYPE	
		SYNTAX		NPTSNMPYesOrNo
		MAX-ACCESS	read-only
		STATUS		current
		DESCRIPTION	"Wavelength Tuning"
		::=  {  nptTunnableTransceiverConfigurationEntry  7  }
		
	nptTxDitherSupport	 	OBJECT-TYPE	
		SYNTAX		NPTSNMPYesOrNo
		MAX-ACCESS	read-only
		STATUS		current
		DESCRIPTION	"Tx Dither Support"
		::=  {  nptTunnableTransceiverConfigurationEntry  8  }	
		
	nptFirstFrequency 	OBJECT-TYPE	
		SYNTAX		DisplayString
		MAX-ACCESS	read-only 
		STATUS		current
		DESCRIPTION	"First Frequency"
		::=  {  nptTunnableTransceiverConfigurationEntry  9  }
		
	nptLastFrequency	OBJECT-TYPE	
		SYNTAX		DisplayString
		MAX-ACCESS	read-only
		STATUS		current
		DESCRIPTION	"Last Frequency"
		::=  {  nptTunnableTransceiverConfigurationEntry  10  }	
		
	nptMinimumSupportedGridSpacing 	OBJECT-TYPE	
		SYNTAX		DisplayString
		MAX-ACCESS	read-only
		STATUS		current
		DESCRIPTION	"Minimum Supported GridSpacing"
		::=  {  nptTunnableTransceiverConfigurationEntry  11 }	
		
	nptChassisPowerTable	OBJECT-TYPE
		SYNTAX		SEQUENCE  OF  NptChassisPowerEntry
		MAX-ACCESS	not-accessible
		STATUS		current
		DESCRIPTION	"It is possible to configure up to ten managers, 
				to whom, traps will be sent. It is possible also 
				to define trap filters for each of the managers."
		::=  { nptPowerConsumption  1 }
        
	nptChassisPowerEntry	OBJECT-TYPE
		SYNTAX		NptChassisPowerEntry
		MAX-ACCESS	not-accessible
		STATUS		current
		DESCRIPTION	"Row Description"
		INDEX		{  nptChassisPowerObjectIndex  }
		::=  { nptChassisPowerTable 1 }


	NptChassisPowerEntry  ::=  SEQUENCE {
		nptChassisPowerObjectIndex              Integer32,
		nptChassisPowerObjectName               DisplayString,
		nptChassisPowerCurrentInputDCVoltage    DisplayString,
		nptChassisPowerCurrentInputDCCurrent    DisplayString,
		nptChassisPowerMaxInputDCVoltage        DisplayString,
		nptChassisPowerMinInputDCVoltage        DisplayString,
		nptChassisPowerMaxInputDCCurrent        DisplayString,
		nptChassisPowerMinInputDCCurrent        DisplayString,
		nptChassisPowerCurrentPowerConsumption  DisplayString,
		nptChassisPowerShelfPowerConsumption    DisplayString,
		nptChassisPowerMaxOutputPower           DisplayString
		}


	nptChassisPowerObjectIndex	OBJECT-TYPE	
		SYNTAX			Integer32  ( -2147483648 .. 2147483647  ) 
		MAX-ACCESS		read-only
		STATUS			current
		DESCRIPTION		"Column Description"
		::=  {  nptChassisPowerEntry  1  }

	nptChassisPowerObjectName	OBJECT-TYPE	
		SYNTAX			DisplayString
		MAX-ACCESS		read-only
		STATUS			current
		DESCRIPTION		"Column Description"
		::=  {  nptChassisPowerEntry  2  }

	nptChassisPowerCurrentInputDCVoltage	OBJECT-TYPE	
		SYNTAX			DisplayString
		MAX-ACCESS		read-only
		STATUS			current
		DESCRIPTION		"Column Description"
		::=  {  nptChassisPowerEntry  3  }

	nptChassisPowerCurrentInputDCCurrent	OBJECT-TYPE	
		SYNTAX			DisplayString
		MAX-ACCESS		read-only
		STATUS			current
		DESCRIPTION		"W"
		::=  {  nptChassisPowerEntry  4  }

	nptChassisPowerMaxInputDCVoltage	OBJECT-TYPE	
		SYNTAX			DisplayString
		MAX-ACCESS		read-only
		STATUS			current
		DESCRIPTION		"W"
		::=  {  nptChassisPowerEntry  5  }

	nptChassisPowerMinInputDCVoltage	OBJECT-TYPE	
		SYNTAX			DisplayString
		MAX-ACCESS		read-only
		STATUS			current
		DESCRIPTION		"W"
		::=  {  nptChassisPowerEntry  6  }

	nptChassisPowerMaxInputDCCurrent	OBJECT-TYPE	
		SYNTAX			DisplayString
		MAX-ACCESS		read-only
		STATUS			current
		DESCRIPTION		"W"
		::=  {  nptChassisPowerEntry  7  }

	nptChassisPowerMinInputDCCurrent	OBJECT-TYPE	
		SYNTAX			DisplayString
		MAX-ACCESS		read-only
		STATUS			current
		DESCRIPTION		"W"
		::=  {  nptChassisPowerEntry  8  }

	nptChassisPowerCurrentPowerConsumption	OBJECT-TYPE	
		SYNTAX			DisplayString
		MAX-ACCESS		read-only
		STATUS			current
		DESCRIPTION		"W"
		::=  {  nptChassisPowerEntry  9  }

	nptChassisPowerShelfPowerConsumption	OBJECT-TYPE	
		SYNTAX			DisplayString
		MAX-ACCESS		read-only
		STATUS			current
		DESCRIPTION		"W"
		::=  {  nptChassisPowerEntry  10  }

	nptChassisPowerMaxOutputPower	OBJECT-TYPE	
		SYNTAX			DisplayString
		MAX-ACCESS		read-only
		STATUS			current
		DESCRIPTION		"W"
		::=  {  nptChassisPowerEntry  11  }
         
         
	nptShelfPowerTable	OBJECT-TYPE
		SYNTAX		SEQUENCE  OF  NptShelfPowerEntry
		MAX-ACCESS	not-accessible
		STATUS		current
		DESCRIPTION	"It is possible to configure up to ten managers, 
				to whom, traps will be sent. It is possible also 
				to define trap filters for each of the managers."
		::=  { nptPowerConsumption  2 }
        
	nptShelfPowerEntry	OBJECT-TYPE
		SYNTAX		NptShelfPowerEntry
		MAX-ACCESS	not-accessible
		STATUS		current
		DESCRIPTION	"Row Description"
		INDEX		{  nptShelfPowerObjectIndex  }
		::=  { nptShelfPowerTable 1 }


	NptShelfPowerEntry  ::=  SEQUENCE {
		nptShelfPowerObjectIndex              Integer32,
		nptShelfPowerObjectName               DisplayString,
		nptShelfPowerTotalPowerBudget         DisplayString,
		nptShelfPowerAssignedBudget           DisplayString,
		nptShelfPowerRemainingBudget          DisplayString,
		nptShelfPowerStatus                   DisplayString,
		nptShelfPowerActualPowerConsumption   DisplayString
		}


	nptShelfPowerObjectIndex	OBJECT-TYPE	
		SYNTAX			Integer32  ( -2147483648 .. 2147483647  ) 
		MAX-ACCESS		read-only
		STATUS			current
		DESCRIPTION		"Column Description"
		::=  {  nptShelfPowerEntry  1  }

	nptShelfPowerObjectName	OBJECT-TYPE	
		SYNTAX			DisplayString
		MAX-ACCESS		read-only
		STATUS			current
		DESCRIPTION		"Column Description"
		::=  {  nptShelfPowerEntry  2  }

	nptShelfPowerTotalPowerBudget	OBJECT-TYPE	
		SYNTAX			DisplayString
		MAX-ACCESS		read-only
		STATUS			current
		DESCRIPTION		"Column Description"
		::=  {  nptShelfPowerEntry  3  }

	nptShelfPowerAssignedBudget	OBJECT-TYPE	
		SYNTAX			DisplayString
		MAX-ACCESS		read-only
		STATUS			current
		DESCRIPTION		"W"
		::=  {  nptShelfPowerEntry  4  }

	nptShelfPowerRemainingBudget	OBJECT-TYPE	
		SYNTAX			DisplayString
		MAX-ACCESS		read-only
		STATUS			current
		DESCRIPTION		"W"
		::=  {  nptShelfPowerEntry  5  }

	nptShelfPowerStatus	OBJECT-TYPE	
		SYNTAX			DisplayString
		MAX-ACCESS		read-only
		STATUS			current
		DESCRIPTION		"Description"
		::=  {  nptShelfPowerEntry  6  }

	nptShelfPowerActualPowerConsumption	OBJECT-TYPE	
		SYNTAX			DisplayString
		MAX-ACCESS		read-only
		STATUS			current
		DESCRIPTION		"W"
		::=  {  nptShelfPowerEntry  7  }

	nptFanStateTable	OBJECT-TYPE
		SYNTAX		SEQUENCE  OF  NptFanStateEntry
		MAX-ACCESS	not-accessible
		STATUS		current
		DESCRIPTION	"It is possible to configure up to ten managers, 
				to whom, traps will be sent. It is possible also 
				to define trap filters for each of the managers."
		::=  { nptChassisEnvironment  1 }
        
	nptFanStateEntry	OBJECT-TYPE
		SYNTAX		NptFanStateEntry
		MAX-ACCESS	not-accessible
		STATUS		current
		DESCRIPTION	"Row Description"
		INDEX		{  nptFanStateIndex  }
		::=  { nptFanStateTable 1 }

	NptFanStateEntry  ::=  SEQUENCE {
		nptFanStateIndex                    Integer32,
		nptFanStateObjectName               DisplayString,
		nptFanStateTurboMode                DisplayString,
        nptFanStateSpeed                    DisplayString,
        nptFanStateLevel                    DisplayString,
        nptFanStatePowerVoltage             DisplayString
		}

	nptFanStateIndex	OBJECT-TYPE	
		SYNTAX			Integer32  ( -2147483648 .. 2147483647  ) 
		MAX-ACCESS		read-only
		STATUS			current
		DESCRIPTION		"Column Description"
		::=  {  nptFanStateEntry  1  }

	nptFanStateObjectName	OBJECT-TYPE	
		SYNTAX			DisplayString
		MAX-ACCESS		read-only
		STATUS			current
		DESCRIPTION		"Column Description"
		::=  {  nptFanStateEntry  2  }

	nptFanStateTurboMode	OBJECT-TYPE	
		SYNTAX			DisplayString
		MAX-ACCESS		read-only
		STATUS			current
		DESCRIPTION		"W"
		::=  {  nptFanStateEntry  3  }

	nptFanStateSpeed	OBJECT-TYPE	
		SYNTAX			DisplayString
		MAX-ACCESS		read-only
		STATUS			current
		DESCRIPTION		"W"
		::=  {  nptFanStateEntry  4  }

	nptFanStateLevel	OBJECT-TYPE	
		SYNTAX			DisplayString
		MAX-ACCESS		read-only
		STATUS			current
		DESCRIPTION		"Description"
		::=  {  nptFanStateEntry  5  }

	nptFanStatePowerVoltage	OBJECT-TYPE	
		SYNTAX			DisplayString
		MAX-ACCESS		read-only
		STATUS			current
		DESCRIPTION		"Description"
		::=  {  nptFanStateEntry  6  }
        
	nptFanUnitStateTable	OBJECT-TYPE
		SYNTAX		SEQUENCE  OF  NptFanUnitStateEntry
		MAX-ACCESS	not-accessible
		STATUS		current
		DESCRIPTION	"It is possible to configure up to ten managers, 
				to whom, traps will be sent. It is possible also 
				to define trap filters for each of the managers."
		::=  { nptChassisEnvironment  2 }
        
	nptFanUnitStateEntry	OBJECT-TYPE
		SYNTAX		NptFanUnitStateEntry
		MAX-ACCESS	not-accessible
		STATUS		current
		DESCRIPTION	"Row Description"
		INDEX		{  nptFanUnitStateID  }
		::=  { nptFanUnitStateTable 1 }

	NptFanUnitStateEntry  ::=  SEQUENCE {
		nptFanUnitStateID              Integer32,
		nptFanUnitStateObjectName               DisplayString,
		nptFanUnitStateRPM                      Integer32,
		nptFanUnitStateLevel                    DisplayString,
		nptFanUnitStateStatus                   DisplayString
		}

	nptFanUnitStateID	OBJECT-TYPE	
		SYNTAX			Integer32  ( -2147483648 .. 2147483647  ) 
		MAX-ACCESS		read-only
		STATUS			current
		DESCRIPTION		"Column Description"
		::=  {  nptFanUnitStateEntry  1  }

	nptFanUnitStateObjectName	OBJECT-TYPE	
		SYNTAX			DisplayString
		MAX-ACCESS		read-only
		STATUS			current
		DESCRIPTION		"Column Description"
		::=  {  nptFanUnitStateEntry  2  }

	nptFanUnitStateRPM	OBJECT-TYPE	
		SYNTAX			Integer32
		MAX-ACCESS		read-only
		STATUS			current
		DESCRIPTION		"W"
		::=  {  nptFanUnitStateEntry  3  }

	nptFanUnitStateLevel	OBJECT-TYPE	
		SYNTAX			DisplayString
		MAX-ACCESS		read-only
		STATUS			current
		DESCRIPTION		"W"
		::=  {  nptFanUnitStateEntry  4  }

	nptFanUnitStateStatus	OBJECT-TYPE	
		SYNTAX			DisplayString
		MAX-ACCESS		read-only
		STATUS			current
		DESCRIPTION		"Description"
		::=  {  nptFanUnitStateEntry  5  }
		 
	nptCardTemperatureTable 	OBJECT-TYPE	
		SYNTAX		SEQUENCE  OF  NptCardTemperatureEntry
		MAX-ACCESS	not-accessible
		STATUS		current
		DESCRIPTION	"Description"
		::=  { nptChassisEnvironment  3 }
	
	nptCardTemperatureEntry	OBJECT-TYPE
		SYNTAX		NptCardTemperatureEntry
		MAX-ACCESS 		not-accessible
		STATUS			current
		DESCRIPTION		"Row Description"
		INDEX			{	nptSlotIndex	}
		::=	 { nptCardTemperatureTable 1 }
		
		NptCardTemperatureEntry	::=  SEQUENCE {
		nptSlotIndex	Unsigned32,
		nptCardName		DisplayString,
		nptStatus		DisplayString,
		nptTemperature	DisplayString,
		nptHighAlarmThreshold	DisplayString,
		nptHighWarnThreshold	DisplayString,
		nptLowAlarmThreshold	DisplayString,
		nptLowWarnThreshold		DisplayString
		}
		
	nptSlotIndex	OBJECT-TYPE	
		SYNTAX		Unsigned32  ( 0 .. 4294967295  )
		MAX-ACCESS	read-only
		STATUS		current
		DESCRIPTION	"Slot Number"
		::=	{ nptCardTemperatureEntry 1 }
		
	nptCardName	 	OBJECT-TYPE
		SYNTAX		DisplayString
		MAX-ACCESS	read-only
		STATUS		current
		DESCRIPTION	"Card Name"	
		::=	{ nptCardTemperatureEntry 2 }
		
	nptStatus		OBJECT-TYPE
		SYNTAX		DisplayString
		MAX-ACCESS	read-only
		STATUS		current
		DESCRIPTION	"Card Status"	
		::=	{ nptCardTemperatureEntry 3 }
		
	nptTemperature	OBJECT-TYPE
		SYNTAX		DisplayString
		MAX-ACCESS	read-only
		STATUS		current
		DESCRIPTION	"Temperature"	
		::=	{ nptCardTemperatureEntry 4 }
		
	nptHighAlarmThreshold	OBJECT-TYPE
		SYNTAX		DisplayString
		MAX-ACCESS	read-only
		STATUS		current
		DESCRIPTION	"High Alarm Threshold"	
		::=	{ nptCardTemperatureEntry 5 }
		
	nptHighWarnThreshold	OBJECT-TYPE
		SYNTAX		DisplayString
		MAX-ACCESS	read-only
		STATUS		current
        DESCRIPTION	"High Warn Threshold"	
		::=	{ nptCardTemperatureEntry 6 }
		
	nptLowAlarmThreshold	OBJECT-TYPE
		SYNTAX		DisplayString
		MAX-ACCESS	read-only
		STATUS		current
		DESCRIPTION	"Low Alarm Threshold"	
		::=	{ nptCardTemperatureEntry 7 }
		
	nptLowWarnThreshold		OBJECT-TYPE
		SYNTAX		DisplayString
		MAX-ACCESS	read-only
		STATUS		current
		DESCRIPTION	"Low Warn Threshold"	
		::=	{ nptCardTemperatureEntry 8 }	
END
