-- File Name : NPT-TRAP-MIB
-- Date      : Thu Jun 09 18:50:03 CST 2011
-- Author    : AdventNet Agent Toolkit C Edition - MibEditor 6



NPT-TRAP-MIB	DEFINITIONS ::= BEGIN
	IMPORTS
		nptTrap
			FROM NPT-ROOT-MIB
		RowStatus, DateAndTime, TEXTUAL-CONVENTION, DisplayString
			FROM SNMPv2-TC
		DisplayString
			FROM RFC1213-MIB
		MODULE-IDENTITY, OBJECT-TYPE, Integer32, enterprises, NOTIFICATION-TYPE
			FROM SNMPv2-SMI
        nptObjectId, nptAlarmId, nptAlarmName, nptAlarmDescription, nptAlarmSeverity, nptAlarmType, nptNeId, nptAlarmTimeStamp, nptAlarmAddtionalinfo
            FROM NPT-ALARM-MIB;

   equipment-Detected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment card detected"
        ::= { nptTrap 2000 }

   equipment-Swap-In NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment swapped in"
        ::= { nptTrap 2001 }

   equipment-Swap-Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment swapped out"
        ::= { nptTrap 2002 }

   type-Unknown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment type unknown"
        ::= { nptTrap 2003 }

   equipment-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment type mismatch"
        ::= { nptTrap 2004 }

   card-Underutilized NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassignable to high capacity card"
        ::= { nptTrap 2005 }

   hW-Rev-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW Revision mismatched"
        ::= { nptTrap 2006 }

   equipment-Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment out"
        ::= { nptTrap 2007 }

   card-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card HW Fail"
        ::= { nptTrap 2008 }

   power-Failures NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Power supply failures"
        ::= { nptTrap 2009 }

   temp-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High temperature"
        ::= { nptTrap 2010 }

   temp-High-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High temperature warning"
        ::= { nptTrap 2011 }

   temp-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low temperature"
        ::= { nptTrap 2012 }

   temp-Low-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low temperature warning"
        ::= { nptTrap 2013 }

   lock-Open NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Lock mechanism unlocked"
        ::= { nptTrap 2014 }

   poE-Over-Voltage NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE power supply over-voltage"
        ::= { nptTrap 2015 }

   poE-Under-Voltage NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE power supply under-voltage"
        ::= { nptTrap 2016 }

   poE-Voltage-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE Power supply low than"
        ::= { nptTrap 2017 }

   bIT-Failed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW failed"
        ::= { nptTrap 2018 }

   bIT-Not-OK NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: input signal failed or degraded."
        ::= { nptTrap 2019 }

   bIT-Degraded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW degraded"
        ::= { nptTrap 2020 }

   bIT-Slightly-Degraded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW slightly degraded"
        ::= { nptTrap 2021 }

   communication-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low layer communication failed"
        ::= { nptTrap 2022 }

   card-Ctrl-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card Not Responding to MCP"
        ::= { nptTrap 2023 }

   card-Patch-Install-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch installation failed"
        ::= { nptTrap 2024 }

   version-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SW version mismatched"
        ::= { nptTrap 2025 }

   cfg-Restore-Success NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Configuration recovered successfully"
        ::= { nptTrap 2026 }

   cfg-Restore-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Configuration recovery failed"
        ::= { nptTrap 2027 }

   cFG-Inconsistency NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card configuration inconsistent with MCP"
        ::= { nptTrap 2028 }

   warm-Reset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Warm reset happened"
        ::= { nptTrap 2029 }

   cold-Reset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Cold reset happened"
        ::= { nptTrap 2030 }

   card-reassigned NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card reassigned"
        ::= { nptTrap 2031 }

   card-Reassign-Notification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card reassign notification"
        ::= { nptTrap 2032 }

   cPU-Utilization-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CPU utilization over threshold Alert"
        ::= { nptTrap 2033 }

   free-Mem-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Memory usage over threshold Alert"
        ::= { nptTrap 2034 }

   mem-Fragmentation NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Max memory block size lower than threshold"
        ::= { nptTrap 2035 }

   free-NVM-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM usage over threshold Alert"
        ::= { nptTrap 2036 }

   dC-IN-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No Power input"
        ::= { nptTrap 2037 }

   dC-IN-A-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No power input at port A"
        ::= { nptTrap 2038 }

   dC-IN-B-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No power input at port B"
        ::= { nptTrap 2039 }

   fan-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan fail"
        ::= { nptTrap 2040 }

   fan-Filter-Change-Reminder NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan filter cleaning Alert"
        ::= { nptTrap 2041 }

   fan-Filter-Missing NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan Filter is missing"
        ::= { nptTrap 2042 }

   eNV-Temp-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Environment temperature High"
        ::= { nptTrap 2043 }

   eNV-Temp-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Environment temperature Low"
        ::= { nptTrap 2044 }

   ext-Alm1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #1"
        ::= { nptTrap 2045 }

   ext-Alm2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #2"
        ::= { nptTrap 2046 }

   ext-Alm3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #3"
        ::= { nptTrap 2047 }

   ext-Alm4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #4"
        ::= { nptTrap 2048 }

   hA-Switchover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Switch over happened"
        ::= { nptTrap 2049 }

   card-Protection-switch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card protection switch happened"
        ::= { nptTrap 2050 }

   nVM-Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM is swapped out"
        ::= { nptTrap 2051 }

   nVM-Lock-Open NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM cover not locked"
        ::= { nptTrap 2052 }

   nVM-Replaced NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM is replaced"
        ::= { nptTrap 2053 }

   sync-Channel-Disconnected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Channel Disconnected"
        ::= { nptTrap 2054 }

   cFG-Sync-Failed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG Sync Failed"
        ::= { nptTrap 2055 }

   dP-Audit-Overwrite-Fai NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DP Configuration Audit Failed"
        ::= { nptTrap 2056 }

   standby-Sync-Channel-Disconnected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Channel Disconnected"
        ::= { nptTrap 2057 }

   heat-Up-Rapidly NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Ambient temperature changes rapidly"
        ::= { nptTrap 2058 }

   iDM-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Object ID mismatched"
        ::= { nptTrap 2059 }

   default-MAC-In-Use NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Default base MAC is used in DP"
        ::= { nptTrap 2060 }

   dC-OUT-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No DC power output"
        ::= { nptTrap 2061 }

   pS-48v-OUT-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No 48v power output"
        ::= { nptTrap 2062 }

   fan-PS-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No 12v power to FAN"
        ::= { nptTrap 2063 }

   reassign-fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassign operation is failed"
        ::= { nptTrap 2064 }

   reassign-success NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassign operation is successful"
        ::= { nptTrap 2065 }

   dying-Gasp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The equipment is going power down"
        ::= { nptTrap 2066 }

   mCP2NP-Heartbeat-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MCP to NP Heart beat detection is failed."
        ::= { nptTrap 2067 }

   fan-In-Turbo NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The fans are running at full speed"
        ::= { nptTrap 2068 }

   pTP-DP-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW not support high accuracy PTP"
        ::= { nptTrap 2069 }

   hW-Rev-Need-Approval NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card usage restricted due to limitation in HW revision"
        ::= { nptTrap 2070 }

   card-OperState-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card operational state is down"
        ::= { nptTrap 2071 }

   power-in-Anomaly NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transient power-in anomaly"
        ::= { nptTrap 2072 }

   gnss-Warm-Reset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS Warm reset happened"
        ::= { nptTrap 2073 }

   gnss-Cold-Reset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS Cold reset happened"
        ::= { nptTrap 2074 }

   gnss-Restore-Factory-Set NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS restores to factory setting"
        ::= { nptTrap 2075 }

   reset-Request-Pending NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reset action Required"
        ::= { nptTrap 2076 }

   part-ID-Verify-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PART-ID verification failed"
        ::= { nptTrap 2200 }

   type-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transceiver type mismatched"
        ::= { nptTrap 2201 }

   appCode-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Application code mismatched"
        ::= { nptTrap 2202 }

   wavelength-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wavelength mismatched"
        ::= { nptTrap 2203 }

   tx-Power-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Power High"
        ::= { nptTrap 2204 }

   tx-Power-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Power Low"
        ::= { nptTrap 2205 }

   rx-Power-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx Power High"
        ::= { nptTrap 2206 }

   rx-Power-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx PowerLow"
        ::= { nptTrap 2207 }

   tx-Laser-Bias-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-High"
        ::= { nptTrap 2208 }

   tx-Laser-Bias-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-Low"
        ::= { nptTrap 2209 }

   tx-Laser-Bias-High-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-High-Warning"
        ::= { nptTrap 2210 }

   tx-Laser-Bias-Low-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-Low-Warning"
        ::= { nptTrap 2211 }

   tx-Power-High-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Power-High-Warning"
        ::= { nptTrap 2212 }

   tx-Power-Low-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Power-Low-Warning"
        ::= { nptTrap 2213 }

   rx-Power-High-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx-Power-High-Warning"
        ::= { nptTrap 2214 }

   rx-Power-Low-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx-Power-Low-Warning"
        ::= { nptTrap 2215 }

   rx-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal"
        ::= { nptTrap 2216 }

   low-Input-OSNR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Input OSNR"
        ::= { nptTrap 2217 }

   sW-Rx-Power-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Used defined Rx Power High"
        ::= { nptTrap 2218 }

   sW-Rx-Power-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Rx Power Low"
        ::= { nptTrap 2219 }

   sW-Tx-Power-High NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Tx Power High"
        ::= { nptTrap 2220 }

   sW-Tx-Power-Low NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Tx Power Low"
        ::= { nptTrap 2221 }

   transceiver-License-Not-Available NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transceiver-License-Not-Available"
        ::= { nptTrap 2222 }

   mCP-Start-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MCP failed to start up"
        ::= { nptTrap 2300 }

   mCP-Start-In-Debug NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The MCP is started in debug mode"
        ::= { nptTrap 2301 }

   hW-CFG-Sync-Suspect NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW configuration may be inconsistent with configuration DB"
        ::= { nptTrap 2302 }

   nE-Restart-Notification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-Restart-Notification"
        ::= { nptTrap 2303 }

   nE-Upgrade-Notification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-Upgrade-Notification"
        ::= { nptTrap 2304 }

   standby-SW-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-SW-Mismatch"
        ::= { nptTrap 2305 }

   standby-CFG-Sync-Failed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-CFG-Sync-Failed"
        ::= { nptTrap 2306 }

   nE-DB-update NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-DB-update"
        ::= { nptTrap 2307 }

   patch-update NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch-update"
        ::= { nptTrap 2308 }

   system-Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "System-Error"
        ::= { nptTrap 2309 }

   system-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "System-Fault"
        ::= { nptTrap 2310 }

   cfg-Save-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Cfg-Save-Fail"
        ::= { nptTrap 2311 }

   cFG-DB-Integrity NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-DB-Integrity"
        ::= { nptTrap 2312 }

   version-activation-fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Version-activation-fail"
        ::= { nptTrap 2313 }

   patch-activation-fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch-activation-fail"
        ::= { nptTrap 2314 }

   lCT-Master-Login NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Login"
        ::= { nptTrap 2316 }

   lCT-Master-Request NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Request"
        ::= { nptTrap 2317 }

   lCT-Master-Logout NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Logout"
        ::= { nptTrap 2318 }

   cLI-Login NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Login"
        ::= { nptTrap 2319 }

   cLI-Logout NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Logout"
        ::= { nptTrap 2320 }

   cLI-In-Config-Mode NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-In-Config-Mode"
        ::= { nptTrap 2321 }

   cLI-Exit-Config-Mode NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Exit-Config-Mode"
        ::= { nptTrap 2322 }

   security-verify-fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Security-verify-fail"
        ::= { nptTrap 2323 }

   cLI-Config-Request NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Config-Request"
        ::= { nptTrap 2324 }

   cLI-Config-Update NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Config-Update"
        ::= { nptTrap 2325 }

   rTC-Request NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "RTC-Request"
        ::= { nptTrap 2326 }

   rTC-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "RTC-Change"
        ::= { nptTrap 2327 }

   mNG-Port-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Gateway NE uplink is down"
        ::= { nptTrap 2328 }

   shelf-Replaced NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Shelf-Replaced"
        ::= { nptTrap 2329 }

   e-Shelf-Detected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "E-Shelf-Detected"
        ::= { nptTrap 2330 }

   pWR-Consumption-TC-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PWR-Consumption-TC-Alarm"
        ::= { nptTrap 2331 }

   pWR-Consumption-TC-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PWR-Consumption-TC-Warning"
        ::= { nptTrap 2332 }

   lICENSE-TO-BE-EXPIRED NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Temporary license will expire in 30 days"
        ::= { nptTrap 2333 }

   lICENSE-EXPIRED NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "License expired"
        ::= { nptTrap 2334 }

   lICENSE-UPDATE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "License status changed"
        ::= { nptTrap 2335 }

   lICENSE-RETRIEVED NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Permanent License retrieved"
        ::= { nptTrap 2336 }

   standby-Status-Sync-Failed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby Status Synchronization failed"
        ::= { nptTrap 2337 }

   both-Matrix-Standby NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Both matrix cards become standby"
        ::= { nptTrap 2338 }

   dB-Corrupted NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE Configuration DB corrupted"
        ::= { nptTrap 2339 }

   standby-MCP-Sync-Failed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-RCPD-Commit-Failed"
        ::= { nptTrap 2340 }

   lICENSE-STATUS-UNKNOWN NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Licensing status unknown"
        ::= { nptTrap 2341 }

   nE-Upgrade-Suspended NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Upgrade getting suspended"
        ::= { nptTrap 2343 }

   boot-From-USB NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE is booted from USB"
        ::= { nptTrap 2344 }

   shelf-Not-Installed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "E-Shelf-Not-Installed"
        ::= { nptTrap 2450 }

   unknow-MBP-Type NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unknow-E-MBP-Type"
        ::= { nptTrap 2451 }

   mBP-Type-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MBP-Type-Mismatch"
        ::= { nptTrap 2452 }

   zTI-NPT-Register NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ZTI event for EMS to adopt me"
        ::= { nptTrap 2453 }

   lTI-1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "0th timing source: Loss of Timing Input"
        ::= { nptTrap 2500 }

   oOR-1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "0th timing source: Input Clock frequency Out Of Range"
        ::= { nptTrap 2501 }

   lTI-2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1st timing source: Loss of Timing Input"
        ::= { nptTrap 2502 }

   oOR-2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1st timing source: Input Clock frequency Out Of Range"
        ::= { nptTrap 2503 }

   lTI-3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd: timing source: Loss of Timing Input"
        ::= { nptTrap 2504 }

   oOR-3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2nd timing source: Input Clock frequency Out Of Range"
        ::= { nptTrap 2505 }

   lTI-4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd timing source: Loss of Timing Input"
        ::= { nptTrap 2506 }

   oOR-4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd timing source: Input Clock frequency Out Of Range"
        ::= { nptTrap 2507 }

   t3-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of frame on E1/T1"
        ::= { nptTrap 2508 }

   t3-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3 AIS on 2048Kbit/s or 1544Kbit/s"
        ::= { nptTrap 2509 }

   t3-BIT-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on E1 or T1;"
        ::= { nptTrap 2510 }

   t3-HZ-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on 2048KHz"
        ::= { nptTrap 2511 }

   t4-LTO NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T4 output cut-off"
        ::= { nptTrap 2512 }

   tMU-All-Sources-Lost NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No available timing source"
        ::= { nptTrap 2513 }

   timing-Source-Switch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU Synchronization source changed"
        ::= { nptTrap 2514 }

   timing-Mode-Switch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU work mode changed"
        ::= { nptTrap 2515 }

   qL-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU quality level changed"
        ::= { nptTrap 2516 }

   lOL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of lock"
        ::= { nptTrap 2517 }

   qL_LOW_1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 1 timing source"
        ::= { nptTrap 2518 }

   qL_LOW_2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 2 timing source"
        ::= { nptTrap 2519 }

   qL_LOW_3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 3 timing source"
        ::= { nptTrap 2520 }

   qL_LOW_4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 4 timing source"
        ::= { nptTrap 2521 }

   t0_FREQ_TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Current timing reference frequency offset TCA"
        ::= { nptTrap 2522 }

   tMU_HW_FAILURE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Timing unit HW failure"
        ::= { nptTrap 2523 }

   pTP-Slave-Unlocked NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Slave not locked to master"
        ::= { nptTrap 2600 }

   pTP-Master-Unlocked NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Master not locked to timing source"
        ::= { nptTrap 2601 }

   one-PPS-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1PPS loss of signal"
        ::= { nptTrap 2602 }

   announce-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Announce Packets Loss"
        ::= { nptTrap 2604 }

   sync-or-FollowUp-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync or FollowUp Packets Loss"
        ::= { nptTrap 2605 }

   delay-Resp-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Delay Response Packets Loss"
        ::= { nptTrap 2606 }

   slave-Port-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The fails or degrade of primary time reference PTP port, the switching of synchronization source"
        ::= { nptTrap 2612 }

   gM-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GM Clock Switching Event"
        ::= { nptTrap 2613 }

   time-State-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Time State Switching Event"
        ::= { nptTrap 2614 }

   tOD-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of TOD Rx"
        ::= { nptTrap 2618 }

   loss-of-10MHz NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of 10MHz signal input"
        ::= { nptTrap 2619 }

   pPI-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on PDH physical interface"
        ::= { nptTrap 3000 }

   pPI-R-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm Indication Signal (AIS) detected in PDH line Rx direction"
        ::= { nptTrap 3001 }

   pPI-T-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sending AIS in PDH line Tx direction"
        ::= { nptTrap 3002 }

   cVTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 3050 }

   cVTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 3051 }

   e1-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm indication signal of E1"
        ::= { nptTrap 3100 }

   e1-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Frame"
        ::= { nptTrap 3101 }

   e1-CAS-LOMF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of CAS multi-Frame(only For PCM30)"
        ::= { nptTrap 3102 }

   e1-CRC-LOMF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of CRC-4 multi-Frame(only For PCM with CRC)"
        ::= { nptTrap 3103 }

   e1-RAI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Alarm Indication (only For Framed Mode)"
        ::= { nptTrap 3104 }

   e1-SD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2M Signal Degrade"
        ::= { nptTrap 3105 }

   e1-EXC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2M Excessive Bit Error"
        ::= { nptTrap 3106 }

   sPI-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SDH Physical Interface Loss of Signal"
        ::= { nptTrap 3200 }

   sPI-TF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SDH Physical InterfaceTransmit Failure"
        ::= { nptTrap 3201 }

   rS-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Loss of Frame"
        ::= { nptTrap 3202 }

   rS-OOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Out of Frame"
        ::= { nptTrap 3203 }

   rS-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Trace Identification(J0) Mismatch"
        ::= { nptTrap 3204 }

   rS-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3205 }

   rS-ESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3206 }

   rS-SESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3207 }

   rS-BBETC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3208 }

   rS-UASTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3209 }

   rS-OFSTC-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OFS in 15 Minutes Threshold Crossing"
        ::= { nptTrap 3210 }

   rS-ESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3211 }

   rS-SESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3212 }

   rS-BBETC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3213 }

   rS-UASTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3214 }

   rS-OFSTC-24H NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OFS in 24 Hours Threshold Crossing"
        ::= { nptTrap 3215 }

   mS-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multiplex Section Alarm Indication Signal"
        ::= { nptTrap 3216 }

   mS-RDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multiplex Section Remote Defect Indication"
        ::= { nptTrap 3217 }

   mS-SD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS Signal Degrade due to BER exceeding SD threshold"
        ::= { nptTrap 3218 }

   mS-EXC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS Excessive Bit Error and exceeds SF threshold"
        ::= { nptTrap 3219 }

   mSPL-PM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear MSP Protocol mismatch"
        ::= { nptTrap 3220 }

   mSPL-APS-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear MSP APS controller is not working as expected"
        ::= { nptTrap 3221 }

   mS-Protection-Switch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS protection switch event(for MSP 1+1)"
        ::= { nptTrap 3222 }

   mS-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3223 }

   mS-UAT-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 3224 }

   mS-ESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3225 }

   mS-SESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3226 }

   mS-BBETC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3227 }

   mS-UASTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3228 }

   mS-ESTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 3229 }

   mS-SESTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 3230 }

   mS-BBETC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Far End"
        ::= { nptTrap 3231 }

   mS-UASTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 3232 }

   mS-ESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3233 }

   mS-SESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3234 }

   mS-BBETC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3235 }

   mS-UASTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3236 }

   mS-ESTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 3237 }

   mS-SESTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 3238 }

   mS-BBETC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Far End"
        ::= { nptTrap 3239 }

   mS-UASTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS IN 24 Hours Threshold Crossing Far End"
        ::= { nptTrap 3240 }

   aU-LOP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Administration Unit Loss of Pointer"
        ::= { nptTrap 3300 }

   hP-LOM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Loss of Multi-frame"
        ::= { nptTrap 3301 }

   hP-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Alarm Indication Signal"
        ::= { nptTrap 3302 }

   hP-RDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Remote Defect Indication"
        ::= { nptTrap 3303 }

   hP-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Trace Identification(J1) Mismatch"
        ::= { nptTrap 3304 }

   hP-UNEQ NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Unequipped"
        ::= { nptTrap 3305 }

   hP-SLM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Signal Label(C2) Mismatch"
        ::= { nptTrap 3306 }

   hP-SD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-4 Signal Degrade"
        ::= { nptTrap 3307 }

   hP-EXC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-4 Excessive Bit Error (Cross SF threshold)"
        ::= { nptTrap 3308 }

   uAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3350 }

   uAT-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 3351 }

   eSTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3352 }

   sESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3353 }

   bBETC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3354 }

   uASTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3355 }

   eSTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 3356 }

   sESTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 3357 }

   bBETC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Far End"
        ::= { nptTrap 3358 }

   uASTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 3359 }

   eSTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3362 }

   sESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3363 }

   bBETC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3364 }

   uASTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3365 }

   eSTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 3366 }

   sESTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 3367 }

   bBETC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Far End"
        ::= { nptTrap 3368 }

   uASTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS IN 24 Hours Threshold Crossing Far End"
        ::= { nptTrap 3369 }

   tU-LOP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tributary Unit Loss of Pointer"
        ::= { nptTrap 3400 }

   lP-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Alarm Indication Signal"
        ::= { nptTrap 3401 }

   lP-RDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Remote Defect Indication"
        ::= { nptTrap 3402 }

   lP-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Trace Identification Mismatch"
        ::= { nptTrap 3403 }

   lP-UNEQ NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Unequipped"
        ::= { nptTrap 3404 }

   lP-SLM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Signal Label Mismatch"
        ::= { nptTrap 3405 }

   lP-SD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-3/VC-12 Signal Degrade"
        ::= { nptTrap 3406 }

   lP-EXC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-3/VC-12  Excessive Bit Error"
        ::= { nptTrap 3407 }

   pCM-Port-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on interface"
        ::= { nptTrap 3500 }

   line-Rx-Inactivity NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No actvity is detected on Rx port of  V.24 or V.35/v.11"
        ::= { nptTrap 3501 }

   yellow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote defect indication"
        ::= { nptTrap 3502 }

   n-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received N from line is bigger than N configured"
        ::= { nptTrap 3503 }

   line-N-Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The N value received from line is not a valid value"
        ::= { nptTrap 3504 }

   e1-N-Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unable to get valid OH (N and signaling) from E1 channel"
        ::= { nptTrap 3505 }

   external-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm occurs on Dry contact input port"
        ::= { nptTrap 3506 }

   external-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Event occurs on Dry contact input port"
        ::= { nptTrap 3507 }

   rxPsnLOPS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LOPS alarm at PSN to TDM direction"
        ::= { nptTrap 3600 }

   rxPsnStrayPkts NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive stray packet discards at PSN to TDM direction"
        ::= { nptTrap 3601 }

   rxPsnMalformPkts NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive malformed packet discards at PSN to TDM direction"
        ::= { nptTrap 3602 }

   rxPsnBufferOverrun NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive jitter buffer overruns at PSN to TDM direction"
        ::= { nptTrap 3603 }

   rxPsnPLR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive packet loss ratio at PSN to TDM direction"
        ::= { nptTrap 3604 }

   rxPsnPER NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive packet error ratio at PSN to TDM direction"
        ::= { nptTrap 3605 }

   rxPsnFarEndLOPS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote IWF is in LOPS state"
        ::= { nptTrap 3606 }

   rxPsnRecClk NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Recovered clock state is abnormal"
        ::= { nptTrap 3607 }


   cES-Card-Protection-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CES Card Protection Group Switching"
        ::= { nptTrap 3630 }

   cES-Card-Protection-Degrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CES Protecting Card Fails"
        ::= { nptTrap 3631 }


   dS1LOS-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on DS1 physical interface"
        ::= { nptTrap 4000 }

   r-DS1AIS-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Path  Alarm Indication Signal in receive direction"
        ::= { nptTrap 4100 }

   r-DS1AIS-CI-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Path  Alarm Indication Signal - Customer Installation"
        ::= { nptTrap 4101 }

   t-DS1AIS-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1-AIS is sent in line transmit direction."
        ::= { nptTrap 4102 }

   dS1LOF-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Loss of Frame"
        ::= { nptTrap 4103 }

   dS1RAI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Remote Alarm Indication"
        ::= { nptTrap 4104 }

   dS1RAI-CI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Alarm Indication - Customer Installation"
        ::= { nptTrap 4105 }

   dS1P-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 4150 }

   cSSTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CSS in 15 Minutes Threshold Crossing Near End"
        ::= { nptTrap 4151 }

   sASTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SAS in 15 Minutes Threshold Crossing Near End"
        ::= { nptTrap 4152 }

   cSSTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CSS in 24 Hours Threshold Crossing Near End"
        ::= { nptTrap 4153 }

   sASTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SAS in 24 Hours Threshold Crossing Near End"
        ::= { nptTrap 4154 }

   lOF-S NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Section Loss of Frame"
        ::= { nptTrap 4200 }

   tIM-S NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Section Trace Identification(J0) Mismatch"
        ::= { nptTrap 4201 }

   s-ESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 4202 }

   s-SESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 4203 }

   s-CVTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 4204 }

   s-SEFSTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SEFS in 15 Minutes Threshold Crossing"
        ::= { nptTrap 4205 }

   s-ESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 4206 }

   s-SESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 4207 }

   s-CVTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4208 }

   s-SEFSTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SEFS in 24 Hours Threshold Crossing"
        ::= { nptTrap 4209 }

   aIS-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Alarm Indication Signal"
        ::= { nptTrap 4210 }

   rFI-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LIne Remote Defect Indication"
        ::= { nptTrap 4211 }

   sD-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Signal Degrade"
        ::= { nptTrap 4212 }

   eXC-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Excessive Bit Error"
        ::= { nptTrap 4213 }

   l-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 4214 }

   l-UAT-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 4215 }

   l-ESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 4216 }

   l-SESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 4217 }

   l-CVTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 4218 }

   l-UASTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 4219 }

   l-ESTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 4220 }

   l-SESTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 4221 }

   l-CVTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Far End"
        ::= { nptTrap 4222 }

   l-UASTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 4223 }

   l-ESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 4224 }

   l-SESTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 4225 }

   l-CVTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4226 }

   l-CVTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Far End"
        ::= { nptTrap 4227 }

   l-UASTC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 4228 }

   l-ESTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 4229 }

   l-SESTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 4230 }

   l-UASTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Far End"
        ::= { nptTrap 4231 }

   lOP-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Administration Unit Loss of Pointer"
        ::= { nptTrap 4300 }

   lOM-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Loss of Multi-frame"
        ::= { nptTrap 4301 }

   aIS-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path  Alarm Indication Signal"
        ::= { nptTrap 4302 }

   rFI-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS PathRemote Defect Indication"
        ::= { nptTrap 4303 }

   tIM-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Trace Identification(J1) Mismatch"
        ::= { nptTrap 4304 }

   uNEQ-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Unequipped"
        ::= { nptTrap 4305 }

   pLM-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path STS Payload Label Mismatch"
        ::= { nptTrap 4306 }

   sD-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Signal Degrade"
        ::= { nptTrap 4307 }

   eXC-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path  Excessive Bit Error"
        ::= { nptTrap 4308 }

   pDI-P NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Payload Defect Indication"
        ::= { nptTrap 4309 }

   cVTC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Far End"
        ::= { nptTrap 4350 }

   cVTC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4351 }

   lOP-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Loss of Pointer"
        ::= { nptTrap 4400 }

   aIS-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Alarm Indication Signal"
        ::= { nptTrap 4401 }

   rFI-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path  Remote Defect Indication"
        ::= { nptTrap 4402 }

   tIM-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Trace Identification Mismatch"
        ::= { nptTrap 4403 }

   uNEQ-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Unequipped"
        ::= { nptTrap 4404 }

   pLM-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Signal Label Mismatch"
        ::= { nptTrap 4405 }

   sD-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Signal Degrade"
        ::= { nptTrap 4406 }

   eXC-V NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Excessive Bit Error"
        ::= { nptTrap 4407 }

   dS3-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 loss of signal (LOS) defect"
        ::= { nptTrap 4500 }

   dS3-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Alarm indication signal"
        ::= { nptTrap 4501 }

   dS3-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Loss of Frame"
        ::= { nptTrap 4502 }

   dS3-OOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Out of Frame"
        ::= { nptTrap 4503 }

   dS3-IDLE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Idle signal"
        ::= { nptTrap 4504 }

   dS3-RAI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Remote Alarm Indication"
        ::= { nptTrap 4505 }

   dS3-FE-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Loss of signal defect"
        ::= { nptTrap 4506 }

   dS3-FE-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Alarm Indication Signal"
        ::= { nptTrap 4507 }

   dS3-FE-OOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Out of Frame"
        ::= { nptTrap 4508 }

   dS3-FE-IDLE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End IDLE signal received"
        ::= { nptTrap 4509 }

   dS3-FE-EQFS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End equipment failure that is service affecting"
        ::= { nptTrap 4510 }

   dS3-FE-EQFN NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End equipment failure that is non service affecting"
        ::= { nptTrap 4511 }

   dS3-FE-MDS1-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Multiple DS1 loss of signal"
        ::= { nptTrap 4512 }

   dS3-FE-SDS1-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Single DS1 loss of signal"
        ::= { nptTrap 4513 }

   dS3-FE-DS1-EQFS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 equipment failure in the DS3 occurred that is service affecting"
        ::= { nptTrap 4514 }

   dS3-FE-DS1-EQFN NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 equipment failure in the DS3 occurred that is non service affecting"
        ::= { nptTrap 4515 }

   dS3-FE-DS1-CEFN NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 common equipment failure in the DS3 occurred that is non service affecting"
        ::= { nptTrap 4516 }

   dS3-LOS-L NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A DS3 loss of signal (LOS) defect is detected."
        ::= { nptTrap 4550 }

   power-In-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is less than the input LOS threshold."
        ::= { nptTrap 5000 }

   output-Power-Degrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The deviation of output power from the target value exceeds the threshold."
        ::= { nptTrap 5001 }

   power-In-Overload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is out of overload tolerance of the EDFA receiver"
        ::= { nptTrap 5002 }

   power-In-Degrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is lower than the expected degraded threshold of the EDFA receiver"
        ::= { nptTrap 5003 }

   power-In-LOS1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "input power is less than the input LOS threshold at the first stage"
        ::= { nptTrap 5004 }

   power-Out-LOP1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of output signal power at the first stage"
        ::= { nptTrap 5005 }

   power-In-LOS2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "input power is less than the input LOS threshold at the second stage"
        ::= { nptTrap 5006 }

   power-Out-LOP2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of output signal power at the second stage"
        ::= { nptTrap 5007 }

   mid-stage-loss-out-of-range NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Mid-stage loss out of range"
        ::= { nptTrap 5008 }

   gain-OOR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Out Of Required gain on semi/automatic gain control"
        ::= { nptTrap 5009 }

   gain-OOM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Out Of Margin on semi/automatic gain control"
        ::= { nptTrap 5010 }

   oTU-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  signal"
        ::= { nptTrap 5101 }

   oTU-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  frame"
        ::= { nptTrap 5102 }

   oTU-LOM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of multiframe"
        ::= { nptTrap 5103 }

   oTU-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU alarm Indication Signal"
        ::= { nptTrap 5104 }

   oTU-BDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU backward Defect Indication"
        ::= { nptTrap 5105 }

   oTU-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace identifier mismatch in OUT"
        ::= { nptTrap 5106 }

   oTU-DEG NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degraded defect derived from BIP8 calculation."
        ::= { nptTrap 5107 }

   oTU-IAE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incoming alignment error"
        ::= { nptTrap 5108 }

   oTU-BIAE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Backward Incoming alignment error"
        ::= { nptTrap 5109 }

   fCE-EXC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FEC corrected errors - excessive errors present"
        ::= { nptTrap 5110 }

   fCE-DEG NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FEC corrected errors - degraded errors present"
        ::= { nptTrap 5111 }

   oTU-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unavailable time near end"
        ::= { nptTrap 5112 }

   oTU-UAT-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unavailable time far end"
        ::= { nptTrap 5113 }

   oTU-BBE-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 15Min"
        ::= { nptTrap 5114 }

   oTU-BBE-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 15Min"
        ::= { nptTrap 5115 }

   oTU-ES-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 15Min"
        ::= { nptTrap 5116 }

   oTU-ES-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 15Min"
        ::= { nptTrap 5117 }

   oTU-SES-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 15Min"
        ::= { nptTrap 5118 }

   oTU-SES-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 15Min"
        ::= { nptTrap 5119 }

   oTU-CE-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for Corrected Errors accumulated near end in 15Min"
        ::= { nptTrap 5120 }

   oTU-BBE-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 24 hours"
        ::= { nptTrap 5121 }

   oTU-BBE-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 24 hours"
        ::= { nptTrap 5122 }

   oTU-ES-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 24 hours"
        ::= { nptTrap 5123 }

   oTU-ES-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 24 hours"
        ::= { nptTrap 5124 }

   oTU-SES-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 24 hours"
        ::= { nptTrap 5125 }

   oTU-SES-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 24 hours"
        ::= { nptTrap 5126 }

   oTU-CE-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for Corrected Errors accumulated near end in 24 hours"
        ::= { nptTrap 5127 }

   oDU-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU alarm Indication Signal"
        ::= { nptTrap 5200 }

   oDU-OCI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Open Connection Indication"
        ::= { nptTrap 5201 }

   oDU-LCK NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Lock indication"
        ::= { nptTrap 5202 }

   oDU-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Trace identifier mismatch"
        ::= { nptTrap 5203 }

   oDU-PLM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Payload Mismatch"
        ::= { nptTrap 5204 }

   oDU-BDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Backward defect indication"
        ::= { nptTrap 5205 }

   oDU-DEG NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Degraded indication"
        ::= { nptTrap 5206 }

   oDU-CSF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A single-bit OPUk client signal fail"
        ::= { nptTrap 5207 }

   oPU-PN11 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Generic AIS, Indicates client Port LOS"
        ::= { nptTrap 5208 }

   oDU-UAT-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUk Unavailable time near end"
        ::= { nptTrap 5211 }

   oDU-UAT-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUk Unavailable time near end"
        ::= { nptTrap 5212 }

   oDU-BBE-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 15Min"
        ::= { nptTrap 5213 }

   oDU-BBE-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 15Min"
        ::= { nptTrap 5214 }

   oDU-ES-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 15Min"
        ::= { nptTrap 5215 }

   oDU-ES-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 15Min"
        ::= { nptTrap 5216 }

   oDU-SES-TC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 15Min"
        ::= { nptTrap 5217 }

   oDU-SES-TC-15M-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 15Min"
        ::= { nptTrap 5218 }

   oDU-BBE-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 24 hours"
        ::= { nptTrap 5220 }

   oDU-BBE-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 24 hours"
        ::= { nptTrap 5221 }

   oDU-ES-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 24 hours"
        ::= { nptTrap 5222 }

   oDU-ES-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 24 hours"
        ::= { nptTrap 5223 }

   oDU-SES-TC-24H-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 24 hours"
        ::= { nptTrap 5224 }

   oDU-SES-TC-24H-FE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 24 hours"
        ::= { nptTrap 5225 }

   sNC-Protection-Switch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SNCP Protection switched event"
        ::= { nptTrap 5227 }

   oTUC-LOS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  signal"
        ::= { nptTrap 5301 }

   oTUC-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  frame"
        ::= { nptTrap 5302 }

   oTUC-LOM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of multiframe"
        ::= { nptTrap 5303 }

   oTUC-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU alarm Indication Signal"
        ::= { nptTrap 5304 }

   oTUC-BDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU backward Defect Indication"
        ::= { nptTrap 5305 }

   oTUC-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace identifier mismatch in OTUCn"
        ::= { nptTrap 5306 }

   oTUC-DEG NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degraded defect derived from BIP8 calculation."
        ::= { nptTrap 5307 }

   oTUC-IAE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incoming alignment error"
        ::= { nptTrap 5308 }

   oTUC-BIAE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Backward Incoming alignment error"
        ::= { nptTrap 5309 }

   hi-Pre-FEC-BER NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Pre-FEC BER exceeded  its high threshold"
        ::= { nptTrap 5310 }

   oDUC-AIS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn alarm Indication Signal"
        ::= { nptTrap 5401 }

   oDUC-OCI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Open Connection Indication"
        ::= { nptTrap 5402 }

   oDUC-LCK NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Lock indication"
        ::= { nptTrap 5403 }

   oDUC-TIM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Trace identifier mismatch"
        ::= { nptTrap 5404 }

   oDUC-PLM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Payload Mismatch"
        ::= { nptTrap 5405 }

   oDUC-BDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Backward defect indication"
        ::= { nptTrap 5406 }

   oDUC-DEG NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Degraded indication"
        ::= { nptTrap 5407 }

   oDUC-CSF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A single-bit client signal fail"
        ::= { nptTrap 5408 }

   rx-LOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Frame"
        ::= { nptTrap 5800 }

   rx-LOM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Multiple frame"
        ::= { nptTrap 5801 }

   lD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local Degrade"
        ::= { nptTrap 5802 }

   rD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Degrade"
        ::= { nptTrap 5803 }

   portLinkDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Link down"
        ::= { nptTrap 6000 }

   link-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Port operational state down"
        ::= { nptTrap 6001 }

   aN-Ability-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Auto-negotiation resulting in link capacity"
        ::= { nptTrap 6002 }

   autoNeg-Fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Auto-negotiation failed"
        ::= { nptTrap 6003 }

   high-BER NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High BER"
        ::= { nptTrap 6004 }

   lOSYNC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PCS loss of synchronization"
        ::= { nptTrap 6005 }

   pCS-ESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Errored Seconds, 15 minutes"
        ::= { nptTrap 6006 }

   pCS-SESTC-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Severely Errored Seconds, 15 minutes"
        ::= { nptTrap 6007 }

   pCS-CV-15M-NE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Code Violations, 15 minutes"
        ::= { nptTrap 6008 }

   local-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local fault"
        ::= { nptTrap 6009 }

   remote-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote fault"
        ::= { nptTrap 6010 }

   rx-ErrPkts-TC-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Bad Frames, 15 minutes"
        ::= { nptTrap 6011 }

   rx-BCPkts-TC-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Broadcast Frames, 15 minutes"
        ::= { nptTrap 6012 }

   rx-MCPkts-TC-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Multicast Frames, 15 minutes"
        ::= { nptTrap 6013 }

   eXC-BER NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive BER"
        ::= { nptTrap 6014 }

   tx-Port-Utilization-TC-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Tx Port Utilization, 15 minutes"
        ::= { nptTrap 6015 }

   oAM-Discovery-fail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Discovery Failed"
        ::= { nptTrap 6050 }

   oAM-Link-Lost NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Lost Link"
        ::= { nptTrap 6051 }

   oAM-Remote-Link-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Link Fault"
        ::= { nptTrap 6052 }

   oAM-Local-Link-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local Link Event"
        ::= { nptTrap 6053 }

   oAM-Remote-Link-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Link Event"
        ::= { nptTrap 6054 }

   oAM-Local-loopback NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local loop back"
        ::= { nptTrap 6055 }

   oAM-Local-loopback-release NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local loop back release"
        ::= { nptTrap 6056 }

   port-Is-Looped NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Port is looped back"
        ::= { nptTrap 6057 }

   bFD-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD Down"
        ::= { nptTrap 6058 }

   bFD-LOC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD LOC"
        ::= { nptTrap 6059 }

   bFD-RDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD RDI"
        ::= { nptTrap 6060 }

   pD-Disconnect NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Disconnected"
        ::= { nptTrap 6061 }

   pD-Over-current NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Over Current"
        ::= { nptTrap 6062 }

   pD-Short-current NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Short Current"
        ::= { nptTrap 6063 }

   pD-Startup-Over-current NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Startup Over Current"
        ::= { nptTrap 6064 }

   pD-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Fault"
        ::= { nptTrap 6065 }

   oAM-Remote-Link-DyingGasp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Dying Gasp"
        ::= { nptTrap 6066 }

   fRR-InUse-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Frr inuse state is changed"
        ::= { nptTrap 6067 }

   peer-MAC-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Peer MAC Mismatch"
        ::= { nptTrap 6068 }

   lLDP-Remote-Changes NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LLDP Remote Changes"
        ::= { nptTrap 6069 }

   link-Flapping-TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Link Flapping Threshold Crossing"
        ::= { nptTrap 6070 }

   lLDP-Too-Many-Neighbours NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LLDP Too Many Neighbours"
        ::= { nptTrap 6071 }
        
   eSMC-Loss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of ESMC packets"
        ::= { nptTrap 6072 }

   eTH-SD NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Ethernet port signal degraded, when there are CRC detected for the port in the active NPU"
        ::= { nptTrap 6073 }

   pHY-Fault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PHY Fault, specially refers to link-down or failure on the MAC SerDes interface of the Port PHY device."
        ::= { nptTrap 6074 }

   lAG-Partial-Links-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Partial Links are down in the LAG"
        ::= { nptTrap 6100 }

   lAG-Link-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LAG Link down due to the number fo failed ports exceeding the defined threshold"
        ::= { nptTrap 6101 }

   lAG-All-Links-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "All ports in the LAG are down"
        ::= { nptTrap 6102 }

   mC-LAG-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG Protection Switching event"
        ::= { nptTrap 6103 }

   mC-LAG-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG Mismatch due to some reasons"
        ::= { nptTrap 6104 }

   mC-LAG-ICCP-Channel-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG ICCP Channel Down"
        ::= { nptTrap 6105 }

   bridge-Topology-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Topology of span tree instance changed"
        ::= { nptTrap 6120 }

   root-Port-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Root port of STP change"
        ::= { nptTrap 6121 }

   mC-LAG-Unknown-RG-Discarded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unknown RG Discarded for NC-LAG"
        ::= { nptTrap 6122 }

   header-Error-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Header error counter in 15m"
        ::= { nptTrap 6123 }

   tunnel-Resources-Availability-Changes NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tunnel resources available state change events"
        ::= { nptTrap 6124 }

   insert-PE-Time-Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Time out for insert PE action"
        ::= { nptTrap 6125 }

   slow-Path-WRED-Drop-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Slow-Path TM"
        ::= { nptTrap 6126 }

   aRP-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Table is almost full"
        ::= { nptTrap 6127 }

   aRP-NH-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Table for Next Hop is almost full"
        ::= { nptTrap 6128 }

   fIB-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Unicast FIB is full"
        ::= { nptTrap 6129 }

   fIB-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Unicast FIB is almost full"
        ::= { nptTrap 6130 }

   tx-L3VPN-Label-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-L3VPN Label utilization is full"
        ::= { nptTrap 6131 }

   tx-L3VPN-Label-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-L3VPN Label utilization is almost full"
        ::= { nptTrap 6132 }

   iPv4-MC-FIB-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Multicast FIB is full"
        ::= { nptTrap 6133 }

   iPv4-MC-FIB-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Multicast FIB is almost full"
        ::= { nptTrap 6134 }

   iPv6-UC-FIB-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Unicast FIB is full"
        ::= { nptTrap 6135 }

   iPv6-UC-FIB-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Unicast FIB is almost full"
        ::= { nptTrap 6136 }

   iPv6-MC-FIB-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Multicast FIB is full"
        ::= { nptTrap 6137 }

   iPv6-MC-FIB-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Multicast FIB is almost full"
        ::= { nptTrap 6138 }

   tM-Flood-WRED-Drop-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Flood TM"
        ::= { nptTrap 6139 }

   tM-MC-WRED-Drop-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Multicast service TM"
        ::= { nptTrap 6140 }

   bGP-PIC-NH-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP PIC Next Hop is almost full"
        ::= { nptTrap 6141 }

   bGP-PIC-NH-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP PIC Next Hop is full"
        ::= { nptTrap 6142 }

   nH-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IP-MPLS Next Hop is almost full"
        ::= { nptTrap 6143 }

   nH-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IP-MPLS Next Hop is full"
        ::= { nptTrap 6144 }

   scale-Subnet-FIB-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Scale Subnet Unicast FIB is full"
        ::= { nptTrap 6145 }

   scale-Subnet-FIB-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Scale Subnet Unicast FIB is almost full"
        ::= { nptTrap 6146 }

   iPv6-Host-ARP-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Host ARP entries in DP is full"
        ::= { nptTrap 6147 }

   lack-of-TxMPLS-Resouces NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-SYNC-FAIL errors due to lack of TxMPLS related DP resources."
        ::= { nptTrap 6148 }

   lack-of-DP-Resouces NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "There is an incomplete object in DP due to lack of resources."
        ::= { nptTrap 6149 }

   mH-ES-Mode-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-SYNC-FAIL errors due to lack of TxMPLS related DP resources."
        ::= { nptTrap 6150 }

   too-Many-MH-ES-Links NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "There is an incomplete object in DP due to lack of resources."
        ::= { nptTrap 6151 }

   mAC-Table-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC table is full"
        ::= { nptTrap 6152 }

   mAC-Table-Almost-Full-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC table is almost full"
        ::= { nptTrap 6153 }

   mAC-Move-Events NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC Move Events"
        ::= { nptTrap 6201 }

   eRPS-Topo-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ERPS Topology Change"
        ::= { nptTrap 6202 }

   invalid-MAID NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Invalid MA ID"
        ::= { nptTrap 6203 }

   low-Level-CCM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received lower level CCM"
        ::= { nptTrap 6204 }

   mEP-Not-Configured NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received unexpected MEP ID"
        ::= { nptTrap 6205 }

   mEP-Same-MEPID NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received duplicate MEP ID"
        ::= { nptTrap 6206 }

   cCM-Interval-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incorrect CCM Interval"
        ::= { nptTrap 6207 }

   rx-CCM-Timer-Expired NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CCM timer expired /Connectivity Loss"
        ::= { nptTrap 6208 }

   mEP-Interface-Status NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "AC interface down"
        ::= { nptTrap 6209 }

   mEP-Port-Status NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "AC port down"
        ::= { nptTrap 6210 }

   mEP-RDI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received CCM with RDI bit"
        ::= { nptTrap 6211 }

   rMEP-FD-Not-Compliant-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FD"
        ::= { nptTrap 6212 }

   rMEP-FDV-Not-Compliant-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FDV"
        ::= { nptTrap 6213 }

   rMEP-FDV-Not-Compliant-Bck-15M NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FDV Backward"
        ::= { nptTrap 6214 }

   rMEP-Unavail-Fwd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "unavailability Forward"
        ::= { nptTrap 6215 }

   rMEP-Unavail-Bck NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "unavailability Backward"
        ::= { nptTrap 6216 }

   vFIB-Full NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VSI MAC table is full"
        ::= { nptTrap 6218 }

   linear-Protection-Switching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear Protetion switching"
        ::= { nptTrap 6300 }

   linear-Protection-Type-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "there is an inconsistency for PT in this protection domain."
        ::= { nptTrap 6301 }

   linear-Protection-PSC-Protocol-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Protecting LSP does not receive PSC message in 60s"
        ::= { nptTrap 6302 }

   tunnel-Protection-Degrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary or secondary path fails."
        ::= { nptTrap 6303 }

   tunnel-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary and secondary paths fail."
        ::= { nptTrap 6304 }

   pW-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PW operational state is Down"
        ::= { nptTrap 6350 }

   pW-Redundancy-Switchover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PW Redundancy Switchover"
        ::= { nptTrap 6351 }

   protection-Type-Mismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "there is an inconsistency for PT in this protection domain."
        ::= { nptTrap 6353 }

   protection-Protocol-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Protecting Path does not receive APS message"
        ::= { nptTrap 6354 }

   protection-Degrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary or secondary path fails."
        ::= { nptTrap 6355 }

   protection-Domain-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary and secondary paths fail."
        ::= { nptTrap 6356 }

   ospfFrrPrefixProtectionChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when any change in the ipFrrAltProtectionAvailable attribute value for this destination is caused."
        ::= { nptTrap 6420 }

   oSPF-Virt-IF-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual interface."
        ::= { nptTrap 6421 }

   oSPF-Nbr-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPF neighbor. There is P2P definitions in LIF, then there is only 1 neighbor. Only in case of P2P may be supported on LIF"
        ::= { nptTrap 6422 }

   oSPF-Virt-Nbr-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual neighbor"
        ::= { nptTrap 6423 }

   oSPF-IF-Auth-Failure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual interface authentication key or authentication type conflicts"
        ::= { nptTrap 6424 }

   oSPF-Virt-If-Auth-Failure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "virtual interface authentication key or authentication type conflicts"
        ::= { nptTrap 6425 }

   oSPF-IF-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPF interface state change"
        ::= { nptTrap 6426 }

   isisFrrPrefixProtectionChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when any change in the ipFrrAltProtectionAvailable attribute value for this destination is caused."
        ::= { nptTrap 6469 }

   isisDatabaseOverload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when the system enters or leaves the Overload state."
        ::= { nptTrap 6450 }

   isisManualAddressDrops NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when one of the manual areaAddresses assigned to this system is ignored when computing routes."
        ::= { nptTrap 6451 }

   isisAttemptToExceedMaxSequence NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "this notification is generated when  the sequence number on an LSP we generate wraps the 32-bit sequence counter"
        ::= { nptTrap 6453 }

   isisIDLenMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with a different value for the System ID Length."
        ::= { nptTrap 6455 }

   isisMaxAreaAddressesMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with a different value for the Maximum Area Addresses."
        ::= { nptTrap 6456 }

   isisOwnLSPPurge NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with our systemID and zero age"
        ::= { nptTrap 6457 }

   isisSequenceNumberSkip NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive an LSP with our System ID and different contents"
        ::= { nptTrap 6458 }

   isisAuthenticationTypeFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with the wrong authentication type field."
        ::= { nptTrap 6459 }

   isisAuthenticationFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with an incorrect authentication information field."
        ::= { nptTrap 6460 }

   isisAreaMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a Hello PDU from an IS that does not share any area address"
        ::= { nptTrap 6462 }

   isisRejectedAdjacency NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a Hello PDU from an IS but do not establish an adjacency for some reason."
        ::= { nptTrap 6463 }

   isisLSPTooLargeToPropagate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we attempt to propagate an LSP that is larger than the dataLinkBlockSize for the circuit."
        ::= { nptTrap 6464 }

   isisProtocolsSupportedMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when a non-pseudonode segment 0 LSP is received that has no matching protocols supported."
        ::= { nptTrap 6466 }

   isisAdjacencyChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when an adjacency changes state, entering or leaving state up."
        ::= { nptTrap 6467 }

   isisLSPErrorDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when we receive an LSP with a parse error."
        ::= { nptTrap 6468 }

   isisFrrPrefixProtectionChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when any change in the ipFrrAltProtectionAvailable attribute value for this destination is caused."
        ::= { nptTrap 6469 }


   iSIS-DB-Overload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when the system enters or leaves the Overload state."
        ::= { nptTrap 6470 }

   iSIS-Auth-Type-Failure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with the wrong authentication type field."
        ::= { nptTrap 6471 }

   iSIS-Auth-Failure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with an incorrect authentication information field."
        ::= { nptTrap 6472 }

   iSIS-Adj-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when an adjacency changes state, entering or leaving state up."
        ::= { nptTrap 6473 }

   wred-Drop-Ratio NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of Diffserv-Block"
        ::= { nptTrap 6508 }

   rx-Discard-Pkts-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx Discard Packets  TCA"
        ::= { nptTrap 6520 }

   tx-Discard-Pkts-TC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Discard Packets  TCA"
        ::= { nptTrap 6521 }

   aRP-Message-Drop-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Message Drop Event from DAI"
        ::= { nptTrap 6522 }

   dHCP-Server-IP-MAC-Binding-Contradiction NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DHCP Server IP-MAC Binding Contradiction from DAI"
        ::= { nptTrap 6523 }

   lease-Expiration-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A lease time of  a specific record expires from DAI"
        ::= { nptTrap 6524 }

   nDP-Tracking-Destination-State-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Destination state event based on NDP tracking"
        ::= { nptTrap 6525 }

   nDP-Tracking-Prefix-State-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Prefix state event based on NDP tracking"
        ::= { nptTrap 6526 }

   nDP-DAD-Failure-Event NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Duplicate Address Detection Failure"
        ::= { nptTrap 6527 }

   lDP-Session-Up NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session up"
        ::= { nptTrap 6550 }

   lDP-Session-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6551 }

   lDP-Session-Initialization-Failure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6552 }

   lDP-Session-Down-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6553 }

   maximum-Prefix-TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix TCA"
        ::= { nptTrap 6603 }

   bGP-RIB-Size-TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP RIB Size TCA"
        ::= { nptTrap 6604 }

   maximum-Prefix-Exceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix Exceeded"
        ::= { nptTrap 6605 }

   bGP-Session-Down-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP Session Down"
        ::= { nptTrap 6606 }

   bGP-Max-Prefixes-Exceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix Exceeded"
        ::= { nptTrap 6607 }

   bGP-Maximum-Prefix-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix TCA  Alarm"
        ::= { nptTrap 6608 }

   bGP-RIB-Size-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               ""
        ::= { nptTrap 6609 }

   iGMP-Querier-Wrong-Version-Warning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IGMP Querier Wrong Version Warning"
        ::= { nptTrap 6650 }

   iGMP-Group-Membership-Capacity-Exceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IGMP Group Membership Capacity Exceeded"
        ::= { nptTrap 6651 }

   vRRP-New-VRRP-Master NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "new VRRP Master has been elected"
        ::= { nptTrap 6686 }

   vRRP-Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of VRRP error conditions is detected"
        ::= { nptTrap 6687 }

   vRRP-New-VRRP-Master-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "new VRRP Master has been elected"
        ::= { nptTrap 6688 }

   vRRP-Error-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of VRRP error conditions is detected"
        ::= { nptTrap 6689 }

   pimNeighborLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimNeighborLoss notification signifies the loss of an adjacency with a neighbor."
        ::= { nptTrap 6700 }

   pimInvalidRegister NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInvalidRegister notification signifies that an invalid PIM Register message received by this device."
        ::= { nptTrap 6701 }

   pimInvalidJoinPrune NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInvalidJoinPrune notification signifies that an invalid PIM Join/Prune message received by this device."
        ::= { nptTrap 6702 }

   pimRPMappingChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimRPMappingChange notification signifies a change to the active RP mapping on this device."
        ::= { nptTrap 6703 }

   pimInterfaceElection NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInterfaceElection notification signifies that a new DR or DF elected on a network."
        ::= { nptTrap 6704 }

   vRF-RIB-Size-TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF RIB Size TCA"
        ::= { nptTrap 6720 }

   vRF_IPV4_FIB_TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV4 FIB TCA"
        ::= { nptTrap 6721 }

   vRF_IPV6_FIB_TCA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV6 FIB TCA"
        ::= { nptTrap 6722 }

   vRF_IPV4_INACTIVE_ROUTE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV4 Inactive Route"
        ::= { nptTrap 6723 }

   vRF_IPV6_INACTIVE_ROUTE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV6 Inactive Route"
        ::= { nptTrap 6724 }

   oSPFv3-Nbr-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPFv3 neighbor. There is P2P definitions in LIF, then there is only 1 neighbor. Only in case of P2P may be supported on LIF"
        ::= { nptTrap 6754 }

   oSPFv3-IF-State-Change NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPFv3 interface state change"
        ::= { nptTrap 6755 }

   segment-routing-global-srgb-collision NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global srgb collision"
        ::= { nptTrap 6780 }

   segment-routing-global-sid-collision NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global sid collision"
        ::= { nptTrap 6781 }

   segment-routing-index-out-of-range NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing index out of range"
        ::= { nptTrap 6782 }

   sR-Global-SRGB-Collision-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global srgb collision"
        ::= { nptTrap 6783 }

   sR-Global-SID-Collision-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global sid collision"
        ::= { nptTrap 6784 }

   sR-Index-Out-of-Range-Alarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing index out of range"
        ::= { nptTrap 6785 }

   macsec-seq-over-threshold NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MACSec Sequence over threshold"
        ::= { nptTrap 6800 }

   macsec-seq-rollover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MACSec Sequence over roll from maximum value to zero"
        ::= { nptTrap 6801 }

   mKA-Session-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Down Event"
        ::= { nptTrap 6802 }

   mKA-Session-Up NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Up Event"
        ::= { nptTrap 6803 }

   mKA-Connection-Down NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Down Alarm"
        ::= { nptTrap 6804 }

   lOGA NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Group Alignment Indication"
        ::= { nptTrap 7000 }

   gROUP-NUM-INCONSISTENT NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Group Number Inconsistent"
        ::= { nptTrap 7001 }

   pHY-NUM-INCONSISTENT NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Numbers Inconsistent"
        ::= { nptTrap 7002 }

   pHY-MAP-INCONSISTENT NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Maps Inconsistent"
        ::= { nptTrap 7003 }

   cALENDAR-IN-USE-INCONSISTENT NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar in use Inconsistent"
        ::= { nptTrap 7004 }

   lOF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of FlexE overhead frame."
        ::= { nptTrap 7005 }

   lOMF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of FlexE overhead multi-frame."
        ::= { nptTrap 7006 }

   rPF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote PHY Fault."
        ::= { nptTrap 7007 }

   gNM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Group Number Mismatch"
        ::= { nptTrap 7008 }

   pNM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Number Mismatch"
        ::= { nptTrap 7009 }

   pMAPM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Map Mismatch"
        ::= { nptTrap 7010 }

   cM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar in use Mismatch"
        ::= { nptTrap 7011 }

   cCM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar Configuration Mismatch"
        ::= { nptTrap 7012 }

   sCM NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Message Inconsistent"
        ::= { nptTrap 7013 }

   oH-BLOCK-1-ERROR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Overhead anchor block error"
        ::= { nptTrap 7014 }

   cRC-16-ERROR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CRC16 error of a Flexe instance"
        ::= { nptTrap 7015 }

   c-BIT-ERROR NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "C Bit error"
        ::= { nptTrap 7016 }

   cCM-DYNAMIC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar Configuration Mismatch HW in Dynamic mode"
        ::= { nptTrap 7017 }

   cR-A-FAILED NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar request to use calendar A failed"
        ::= { nptTrap 7018 }

   cR-B-FAILED NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar request to use calendar B failed"
        ::= { nptTrap 7019 }

   lOC-FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Connectivity"
        ::= { nptTrap 7030 }

   rDI-FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Defect Indication"
        ::= { nptTrap 7031 }

   cS-LF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Local Fault"
        ::= { nptTrap 7032 }

   cS-RF NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Remote Fault"
        ::= { nptTrap 7033 }

   cS-LPI NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Low Power Indication"
        ::= { nptTrap 7034 }

   cS-UNEQ NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Un-Equipment"
        ::= { nptTrap 7035 }

   tIM-FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace Identification Mismatch"
        ::= { nptTrap 7036 }

   sF-FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Fail"
        ::= { nptTrap 7037 }

   sD-FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degard"
        ::= { nptTrap 7038 }

   pERIOD-MISMATCH NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FlexE channel OAM period mismatch"
        ::= { nptTrap 7039 }

   lF_FLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local fault on FlexE channel MAC layer"
        ::= { nptTrap 7040 }

   rF_FLEXE  NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote fault on FlexE channel MAC layer"
        ::= { nptTrap 7041 }

   sPP-LINK-DOWN NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SPP Link Down"
        ::= { nptTrap 7050 }

   fLEXE-CHANNEL-SWITCHOVER NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Flexe channel switchover"
        ::= { nptTrap 7051 }

   rsvpTeLspDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of the configured lsps is about to enter the down state from some other state (but not from the notPresent state)"
        ::= { nptTrap 7200 }

   rsvpTeLspUp  NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of the configured lsps is about to leave the down state and transition into some other state (but not into the notPresent state)"
        ::= { nptTrap 7201 }

   rsvpTeLspRerouted NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "An lsp is rerouted"
        ::= { nptTrap 7202 }

   rsvpTeLspReoptimized NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "An lsp is reoptimized."
        ::= { nptTrap 7203 }



END
